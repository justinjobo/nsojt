module tailf-netconf-ncs {
  namespace "http://tail-f.com/ns/netconf/ncs";
  prefix ncsnc;

  import ietf-netconf {
    prefix nc;
  }
  import ietf-netconf-nmda {
    prefix ncds;
  }
  import tailf-netconf-transactions {
    prefix tr;
  }
  import tailf-ncs {
    prefix ncs;
  }
  import tailf-common {
    prefix tailf;
  }

  organization "Tail-f Systems";

  description
    "This module defines extensions to NETCONF for NCS.

     Copyright 2013-2022 Cisco Systems, Inc.
     All rights reserved.
     Permission is hereby granted to redistribute this file without
     modification.";

  revision 2022-09-29 {
    description
      "Released as part of NCS-6.0.

       Added parameter 'ordered-commit' to the 'start-transaction' rpc.";
  }

  revision 2022-04-12 {
    description
      "Released as part of NCS-5.8.

       Changed the when-expression in
       /prepare-transaction/input/dry-run/reverse.

       Added a new case 'case-cli-c' to the choice at
       /prepare-transaction/output/dry-run-result/outformat.";
  }

  revision 2021-12-17 {
    description
      "Released as part of NCS-5.7.

       Updated description of the 'reconcile' container in the
       'service-commit-params' grouping.";
  }

  revision 2021-09-02 {
    description
      "Released as part of NCS-5.6.

       Added parameter 'with-service-meta-data' to the
       'get', 'get-config' and 'get-data' rpcs.";
  }

  revision 2020-06-25 {
    description
      "Released as part of NCS-5.4.

       The dryrun parameter to prepare-transaction has been marked obsolete,
       use the dry-run parameter instead.";
  }

  revision 2019-06-27 {
    description
      "Released as part of NCS-5.2.

       The groupings ncs:ncs-commit-params has changed.";
  }

  revision 2018-06-21 {
    description
      "Released as part of NCS-4.7.

       The groupings ncs:ncs-commit-params has changed.";
  }

  revision 2018-03-01 {
    description
      "Released as part of NCS-4.6.

       Renamed 'dryrun' commit parameter to 'dry-run' and renamed the
       output container from 'dryrun-result' to 'dry-run-result'.

       Removed commit-queue-id leaf in error-info.

       Added 'no-deploy' commit parameter.";
  }

  revision 2017-09-28 {
    description
      "Released as part of NCS-4.5.

       Added new option 'reverse' to 'dryrun' commit parameter.";
  }

  revision 2017-06-14 {
    description
      "Released as part of NCS-4.4.2.

       The groupings ncs:ncs-commit-params has changed.";
  }

  revision 2016-11-24 {
    description
      "Released as part of NCS-4.3.

       Changed output format of 'dryrun' result.";
  }

  revision 2016-05-26 {
    description
      "Released as part of NCS-4.2.

       Changed output format of 'dryrun' result.";
  }

  revision 2014-11-19 {
    description
      "Released as part of NCS-3.3.

       The groupings ncs:ncs-commit-params and ncs:ncs-commit-result
       has changed.

       Changed data type of leaf commit-queue-id from int64 to uint64";
  }

  revision 2014-06-30 {
    description
      "Released as part of NCS-3.2.

       Added new commit parameter 'dryrun'.
       Renamed (broken) 'through-commit-queue' to 'async-commit-queue'.
       Added new commit parameter 'sync-commit-queue'.
       Added 'commit-queue' output parameter.";
  }

  revision 2014-05-20 {
    description
      "Released as part of NCS-3.1.1.1.

       Added no-overwrite to ncs-commit-params.";
  }

  revision 2013-06-18 {
    description
      "Initial revision, released as part of NCS-2.3.";
  }

  augment '/nc:get/nc:input' {
    uses with-service-meta-data-params;
  }

  augment '/nc:get-config/nc:input' {
    uses with-service-meta-data-params;
  }

  augment '/ncds:get-data/ncds:input' {
    uses with-service-meta-data-params;
  }

  augment "/nc:commit/nc:input" {
    uses ncs:ncs-commit-params;
    uses service-commit-params;
  }
  augment "/nc:commit/nc:output" {
    uses ncs:ncs-commit-result;
  }

  augment "/nc:edit-config/nc:input" {
    when "nc:target/nc:running";
    uses ncs:ncs-commit-params;
    uses service-commit-params;
  }
  augment "/nc:edit-config/nc:output" {
    uses ncs:ncs-commit-result;
  }

  augment "/nc:copy-config/nc:input" {
    when "nc:target/nc:running";
    uses ncs:ncs-commit-params;
    uses service-commit-params;
  }
  augment "/nc:copy-config/nc:output" {
    uses ncs:ncs-commit-result;
  }

  augment "/tr:start-transaction/tr:input" {
    leaf ordered-commit {
      type empty;
      description
        "Enforces transaction resources, e.g. locks, to be taken in the
         order in which the transactions (with this parameter) are
         started.";
    }
  }

  augment "/tr:prepare-transaction/tr:input" {
    uses ncs:ncs-commit-params;
    uses service-commit-params;
    container dry-run {
      presence "";
      description
        "If the dry-run element is present NCS will return the output
         of what NCS would write to CDB and send to the devices as a
         result of applying the current transaction (using the
         dry-run-result reply). After this rpc the transaction is in the
         same state as it was before the call. I.e. to proceed and
         actually commit the changes, another prepare-transaction is
         required before the commit-transaction rpc.";
      leaf outformat {
        type ncs:outformat3;
        default xml;
      }
      leaf reverse {
        when "(../outformat = 'native') or (../outformat = 'cli-c')";
        type empty;
      }
    }
    container dryrun {
      status obsolete; // will be removed in the next major release
      presence "";
      description
        "If the dryrun element is present NCS will return the output
         of what NCS would write to CDB and send to the devices as a
         result of applying the current transaction (using the
         dry-run-result reply). After this rpc the transaction is in the
         same state as it was before the call. I.e. to proceed and
         actually commit the changes, another prepare-transaction is
         required before the commit-transaction rpc.";
      leaf outformat {
        type ncs:outformat3;
        default xml;
      }
      leaf reverse {
        when "(../outformat = 'native') or (../outformat = 'cli-c')";
        type empty;
      }
    }
  }

  augment "/tr:commit-transaction/tr:output" {
    uses ncs:ncs-commit-result;
  }

  augment "/tr:prepare-transaction/tr:output" {
    container dry-run-result {
      choice outformat {
        case case-xml {
          uses ncs:dry-run-xml;
        }
        case case-cli {
          uses ncs:dry-run-cli;
        }
        case case-native {
          uses ncs:dry-run-native;
        }
        case case-cli-c {
          uses ncs:dry-run-cli-c;
        }
      }
    }
  }

  grouping with-service-meta-data-params {
    leaf with-service-meta-data {
      description
        "Lets the client request that the datastore's
         service meta data is returned in the reply to the request.

         The service meta data is only availabe for the running
         configuration datastore.";
      type empty;
    }
  }

  grouping service-commit-params {
    leaf no-deploy {
      type empty;
      description
        "Commit without invoking the service create method, i.e, write
         the service instance data without activating the service(s).
         The service(s) can later be re-deployed to write the
         changes of the service(s) to the network.";
    }
    container reconcile {
      description
        "Reconcile the service data.  All data which existed before
         the service was created will now be owned by the service.
         When the service is removed that data will also be removed.
         In technical terms the reference count will be decreased
         by one for everything which existed prior to the service.

         If manually configured data exists below in the configuration
         tree that data is kept unless the option
         'discard-non-service-config' is used.";
      presence "Reconcile the service data";
      choice c-non-service-config {
        leaf keep-non-service-config {
          type empty;
        }
        leaf discard-non-service-config {
          type empty;
        }
        default keep-non-service-config;
      }
    }
  }
}
