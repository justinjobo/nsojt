module tailf-ncs {
  yang-version 1.1;
  namespace "http://tail-f.com/ns/ncs";
  prefix ncs;

  include tailf-ncs-common {
    revision-date 2023-04-13;
  }
  include tailf-ncs-cluster {
    revision-date 2021-09-02;
  }
  include tailf-ncs-customers {
    revision-date 2012-08-30;
  }
  include tailf-ncs-devices {
    revision-date 2023-12-19;
  }
  include tailf-ncs-java-vm {
    revision-date 2023-11-16;
  }
  include tailf-ncs-smart-license {
    revision-date 2023-11-16;
  }
  include tailf-ncs-python-vm {
    revision-date 2022-09-29;
  }
  include tailf-ncs-packages {
    revision-date 2024-04-09;
  }
  include tailf-ncs-services {
    revision-date 2023-11-16;
  }
  include tailf-ncs-snmp-notification-receiver {
    revision-date 2012-08-30;
  }
  include tailf-ncs-compliance {
    revision-date 2023-11-16;
  }
  include tailf-ncs-ssh {
    revision-date 2021-09-02;
  }
  include tailf-ncs-software {
    revision-date 2023-11-16;
  }
  include tailf-ncs-plan {
    revision-date 2023-11-16;
  }
  include tailf-ncs-log {
    revision-date 2023-11-16;
  }
  include tailf-ncs-service-progress-monitoring {
    revision-date 2022-09-29;
  }
  include tailf-ncs-high-availability {
    revision-date 2023-04-13;
  }
  include tailf-ncs-metric {
    revision-date 2023-04-13;
  }

  organization "Tail-f Systems";

  description
    "This module defines the Tail-f NCS data model.

     Copyright 2010-2024 Cisco Systems, Inc.
     All rights reserved.
     Permission is hereby granted to redistribute this file without
     modification.";

  revision 2024-04-09 {
    description
      "Released as part of NCS-6.2.4.

       Incorporated updated tailf-ncs-packages submodule.
      ";
  }

  revision 2023-12-19 {
    description
      "Released as part of NCS-6.2.1.

       Incorporated updated tailf-ncs-devices submodule.
      ";
  }

  revision 2023-11-16 {
    description
      "Released as part of NCS-6.2.

       Incorporated updated tailf-ncs-compliance, tailf-ncs-devices,
       tailf-ncs-java-vm, tailf-ncs-plan, tailf-ncs-services,
       tailf-ncs-software, tailf-ncs-packages, tailf-ncs-log and
       tailf-ncs-smart-license submodules.";
  }

  revision 2023-04-13 {
    description
      "Released as part of NCS-6.1.

       Incorporated updated tailf-ncs-plan, tailf-ncs-high-availability,
       tailf-ncs-packages, tailf-ncs-devices, tailf-ncs-common,
       tailf-ncs-compliance, and tailf-ncs-metric submodules.";
  }

  revision 2022-09-29 {
    description
      "Released as part of NCS-6.0.

       Incorporated updated tailf-ncs-devices, tailf-ncs-services,
       tailf-ncs-plan, tailf-ncs-packages, tailf-ncs-smart-license,
       tailf-ncs-python-vm, tailf-ncs-high-availability, and
       tailf-ncs-service-progress-monitoring submodules.

       Added submodule tailf-ncs-metric.";
  }

  revision 2022-04-12 {
    description
      "Released as part of NCS-5.8.

       Incorporated updated tailf-ncs-common, tailf-ncs-devices,
       tailf-ncs-java-vm, tailf-ncs-high-availability, tailf-ncs-plan,
       tailf-ncs-services and tailf-ncs-packages submodules.";
  }

  revision 2021-12-17 {
    description
      "Released as part of NCS-5.7.

       Incorporated updated tailf-ncs-services, tailf-ncs-devices,
       tailf-ncs-plan, tailf-ncs-high-availability, and tailf-ncs-packages
       submodules.";
  }

  revision 2021-10-05 {
    description
      "Released as part of NCS-5.6.1.

       Incorporated updated tailf-ncs-devices submodule.";
  }

  revision 2021-09-02 {
    description
      "Released as part of NCS-5.6.

       Incorporated updated tailf-ncs-cluster, tailf-ncs-packages,
       tailf-ncs-devices, tailf-ncs-services, tailf-ncs-software,
       tailf-ncs-plan, tailf-ncs-java-vm and tailf-ncs-ssh submodules.";
  }

  revision 2021-02-09 {
    description
      "Released as part of NCS-5.5.1.

       Incorporated updated tailf-ncs-plan submodule.";
  }

  revision 2020-11-26 {
    description
      "Released as part of NCS-5.5.

       Incorporated updated tailf-ncs-ssh, tailf-ncs-plan, tailf-ncs-devices
       and tailf-ncs-services submodules.";
  }

  revision 2020-09-10 {
    description
      "Released as part of NCS-5.4.1.

       Incorporated updated tailf-ncs-devices submodule.";
  }

  revision 2020-06-25 {
    description
      "Released as part of NCS-5.4.

       Incorporated updated tailf-ncs-devices, tailf-ncs-packages,
       tailf-ncs-plan, tailf-ncs-services, and tailf-ncs-smart-license
       submodules.

       Added submodule tailf-ncs-high-availability.";
  }

  revision 2020-02-20 {
    description
      "Released as part of NCS-5.3.1.

       Incorporated updated tailf-ncs-devices and tailf-ncs-services
       submodules.";
  }

  revision 2019-11-28 {
    description
      "Released as part of NCS-5.3.

       Incorporated updated tailf-ncs-common, tailf-ncs-cluster,
       tailf-ncs-devices, tailf-ncs-java-vm, tailf-ncs-packages,
       tailf-ncs-ssh, tailf-ncs-software, and tailf-ncs-plan
       submodules.";
  }

  revision 2019-06-27 {
    description
      "Released as part of NCS-5.2.

       Incorporated updated tailf-ncs-devices submodule.";
  }

  revision 2019-05-16 {
    description
      "Released as part of NCS-5.1.1.

       Incorporated updated tailf-ncs-devices submodule.";
  }

  revision 2019-04-09 {
    description
      "Released as part of NCS-5.1.

       Incorporated updated tailf-ncs-devices, tailf-ncs-plan,
       tailf-ncs-services, tailf-ncs-log, tailf-ncs-java-vm and
       tailf-ncs-python-vm submodules.

       Removed tailf-ncs-kicker-extension as submodule.";
  }

  revision 2019-03-07 {
    description
      "Released as part of NCS-4.7.3.

       Incorporated updated tailf-ncs-devices submodule.";
  }

  revision 2018-11-12 {
    description
      "Released as part of NCS-4.7.2.

       Incorporated updated tailf-ncs-plan submodule.";
  }

  revision 2018-04-19 {
    description
      "Released as part of NCS-4.6.1.

       Incorporated updated tailf-ncs-services submodule.";
  }

  revision 2018-03-01 {
    description
      "Released as part of NCS-4.6.

       Incorporated updated tailf-ncs-cluster, tailf-ncs-devices,
       tailf-ncs-python-vm, tailf-ncs-services, and
       tailf-ncs-smart-license submodules.";
  }

  revision 2017-09-28 {
    description
      "Released as part of NCS-4.5.

       Incorporated updated tailf-ncs-smart-license,
       tailf-ncs-cluster, tailf-ncs-devices, tailf-ncs-packages, and
       tailf-ncs-kicker-extension submodules.";
  }

  revision 2017-04-27 {
    description
      "Released as part of NCS-4.4.1.

       Incorporated updated tailf-ncs-devices.";
  }

  revision 2017-03-16 {
    description
      "Released as part of NCS-4.4.

       Incorporated updated tailf-ncs-devices.

       Added range to all config leafs specifying time.";
  }

  revision 2017-01-26 {
    description
      "Released as part of NCS-4.3.1.

       Incorporated updated tailf-ncs-ssh.";
  }

  revision 2016-11-24 {
    description
      "Released as part of NCS-4.3.

       Incorporated updated submodules.

       Added submodule tailf-ncs-log.";
  }

  revision 2016-05-26 {
    description
      "Released as part of NCS-4.2.

       Incorporated updated tailf-ncs-devices, tailf-ncs-services
       submodules, tailf-ncs-packages, and tailf-ncs-compliance.

       Added submodules tailf-ncs-plan and tailf-ncs-smart-license.";
  }

  revision 2016-01-01 {
    description
      "Released as part of NCS-4.2.

       Incorporated updated tailf-ncs-services and tailf-ncs-compliance
       submodules.";
  }

  revision 2016-01-01 {
    description
      "Released as part of NCS-4.1.1.

       Incorporated updated tailf-ncs-devices and tailf-ncs-ssh submodules.";
  }

  revision 2015-10-02 {
    description
      "Released as part of NSO-4.0.2.

       Incorporated updated tailf-ncs-cluster and
       tailf-ncs-services submodules.";
  }

  revision 2015-06-16 {
    description
      "Released as a part of NCS-4.0.

       Incorporated updated tailf-ncs-devices submodule and
       added tailf-ncs-python-vm.";
  }

  revision 2015-03-19 {
    description
      "Released as part of NCS-3.4.

       Incorporated updated tailf-ncs-cluster,
       tailf-ncs-devices, and tailf-ncs-services submodules.";
  }

  revision 2014-12-10 {
    description
      "Released as part of NCS-3.3.1.

       Incorporated updated tailf-ncs-services module.";
  }

  revision 2014-11-19 {
    description
      "Released as part of NCS-3.3.

       Incorporated updated tailf-ncs-devices
       and tailf-ncs-packages submodules, and added
       tailf-ncs-software submodule.";
  }

  revision 2014-06-30 {
    description
      "Released as part of NCS-3.2.

       Incorporated updated tailf-ncs-services, tailf-ncs-devices,
       tailf-ncs-packages, and tailf-ncs-cluster submodules, and added
       tailf-ncs-ssh submodule.";
  }

  revision 2014-05-20 {
    description
      "Released as part of NCS-3.1.1.1";
  }

  revision 2014-05-08 {
    description
      "Released as part of NCS-3.1.1";
  }

  revision 2014-04-02 {
    description
      "Released as part of NCS-3.1.";
  }

  revision 2013-11-12 {
    description
      "Released as part of NCS-3.0.

       Incorporated updated tailf-ncs-services, tailf-ncs-devices,
       and tailf-ncs-packages submodules, and added tailf-ncs-cluster
       and tailf-ncs-compliance submodules.";
  }

  revision 2013-06-18 {
    description
      "Released as part of NCS-2.3.

       Incorporated updated tailf-ncs-services, tailf-ncs-devices,
       and tailf-ncs-packages submodules.";
  }

  revision 2013-04-24 {
    description
      "Released as part of NCS-2.2.1.

       Incorporated updated tailf-ncs-devices submodule.";
  }

  revision 2013-03-12 {
    description
      "Released as part of NCS-2.2.

       Incorporated updated tailf-ncs-devices submodule.";
  }

  revision 2012-11-13 {
    description
      "Released as part of NCS-2.1.

       Incorporated updated tailf-ncs-devices, tailf-ncs-java-vm and
       tailf-ncs-packages submodules.";
  }

  revision 2012-10-04 {
    description
      "Released as part of NCS-2.0.2.

       Incorporated updated tailf-ncs-packages submodule.";
  }

  revision 2012-08-30 {
    description
      "Released as part of NCS-2.0.

       Split tailf-ncs into submodules.

       Removed top-level 'ncs' container moved its contents into three
       separate top-level containers: 'devices', 'services',
       'customers'. Detailed renaming as follows:

         moved /ncs/sm to /services
         moved /ncs/sm/java-vm-startup to /java-vm
         moved /ncs/sm/cust-service to /services/customer-service

         moved /ncs/customers to /customers
         renamed /ncs/customers/cust-service to /customers/customer-service

         moved /ncs/managed-device   to  /devices/device
         moved /ncs/global-settings  to  /devices/global-settings
         moved /ncs/template         to  /devices/template
         moved /ncs/authgroups       to  /devices/authgroups
         moved /ncs/mib-group        to  /devices/mib-group
         moved /ncs/device-group     to  /devices/device-group
         renamed /ncs/device-group/members
                                     to  /devices/device-group/device-name
         moved /ncs/live-device/live-status
                                     to  /devices/device/live-status
         removed /ncs/live-device
         moved /ncs/device-module    to  /devices/device-module
         renamed /ncs/managed-device/device-info to /devices/device/description

         moved /ncs/snmp-notification-receiver to /snmp-notification-receiver

         renamed /ncs/sm/java-vm-startup/enabled to /java-vm/auto-start
         renamed /ncs/sm/java-vm-startup/jvm-start-status to
           /java-vm/start-status
         replaced /ncs/sm/java-vm-startup/synchronization-time with
           /java-vm/connect-time and
           /java-vm/initialization-time
        ";
  }

  revision 2012-03-13 {
    description
      "Released as part of NCS-1.9.

       Replaced /ncs/global/settings/ned-trace and
       /ncs/global/settings/netconf-trace with one leaf
       /ncs/global/settings/trace.

       Replaced /ncs/global/settings/ned-trace-dir and
       /ncs/global/settings/netconf-trace-dir with one leaf
       /ncs/global/settings/trace-dir.

       Added support to control trace per managed device.

       Added /ncs/mib-group and
       /ncs/managed-device/device-type/snmp/mib-group.

       Added support for SNMPv3 notification receivers in
       /ncs/snmp-notification-receiver.

       Added a new parameter 'override-southbound-locked' to
       'connect'.

       Added /ncs/global-settings/write-timeout to control the
       write timeout towards managed devices.

";
  }

  revision 2012-01-31 {
    description
      "Released as part of NCS-1.8.1.

       Made it possible to configure SNMP v3 USM users without any
       authentication or privacy parameters.

       Added /ncs/snmp-notification-receiver to configure NCS as a
       SNMP notification receiver.

       Added /ncs/managed-device/snmp-notification-address.";
  }

  revision 2011-12-13 {
    description
      "Released as part of NCS-1.8.

       Removed the default statement for /ncs/managed-device/port,
       and clarified that the port used by NCS if this leaf is not
       configured depends on the protocol used to communicate with
       the device.

       Changed the name of the leafs
       'ssh-connection-timeout' and 'ssh-read-timeout' under
       /ncs/managed-device to 'connect-timeout' and 'read-timeout',
       respectively.

       Added support for SNMP NEDs.

       /ncs/global-settings/ned-trace is changed from a boolean to an
       enumeration, so that the trace data optionally can be pretty
       printed.";
  }

  revision 2011-09-27 {
    description
      "Released as part of NCS-1.7.";
  }

  revision 2011-06-01 {
    description
      "Released as part of NCS-1.6.";
  }

  revision 2011-03-01 {
    description
      "Released as part of NCS-1.5.";
  }

  revision 2010-11-17 {
    description
      "Released as part of NCS 1.2";
  }

  revision 2010-05-15 {
    description
      "Initial revision, released as part of NCS 1.0";
  }

}
