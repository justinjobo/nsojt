module tailf-confd-monitoring-ann {
  namespace "urn:dummy";
  prefix dummy;

  import tailf-common {
    prefix tailf;
  }
  import tailf-confd-monitoring {
    prefix tfcm;
  }

  description
    "Copyright 2019-2023 Cisco Systems, Inc.
     All rights reserved.
     Permission is hereby granted to redistribute this file without
     modification.";


  revision 2023-04-21 {
    description
      "Released as part of ConfD-8.1.

       Annotate module as an internal data provider with tailf:internal-dp.";
  }

  tailf:annotate "/tfcm:confd-state" {
    tailf:callpoint "confd" {
      tailf:internal;
    }

    tailf:info "Display ConfD status information";
  }

  tailf:annotate-module "tailf-confd-monitoring" {
    tailf:internal-dp;
  }
}
