module cisco-nso-nc-5.8 {
  yang-version 1.1;
  namespace "http://tail-f.com/ns/ned-id/cisco-nso-nc-5.8";
  prefix cisco-nso-nc-5.8;

  import cisco-nso-nc {
    prefix family;
  }

  identity cisco-nso-nc-5.8 {
    base family:cisco-nso-nc;
  }
}
