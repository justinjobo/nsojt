submodule tailf-ncs-compliance {
  // Generated by yanger -t ncs
  tailf:mount-id "cisco-nso-nc-5.8:cisco-nso-nc-5.8";

  yang-version 1.1;
  belongs-to tailf-ncs {
    prefix ncs;
  }

  import tailf-common {
    prefix tailf;
  }
  import ietf-yang-types {
    prefix yang;
  }
  import ietf-inet-types {
    prefix inet;
  }
  include tailf-ncs-devices;
  import tailf-ncs-internal-mount {
    prefix ncs-internal;
  }

  organization
    "Tail-f Systems";
  description
    "This submodule defines the compliance reporting functions
     of NCS.

     Copyright 2013-2016 Cisco Systems, Inc.
     All rights reserved.
     Permission is hereby granted to redistribute this file without
     modification.";

  revision 2016-05-26 {
    description
      "Released as part of NCS-4.2.

       Added /compliance/reports/report/service-checks/historic-changes.
       to be able to report changes from a certain commit interval";
  }
  revision 2013-11-12 {
    description
      "Released as part of NCS-3.0";
  }

  typedef ncs_compliance_template_compliance-status-result {
    type string;
  }

  typedef ncs_template_compliance-status-result {
    type string;
  }

  typedef ncs_rpc_notif_compliance-status-result {
    type enumeration {
      enum "no-violation";
      enum "violations";
    }
  }

  typedef live_ncs_compliance-status-result {
    type enumeration {
      enum "no-violation";
      enum "violations";
    }
  }

  typedef compliance-status-result {
    type enumeration {
      enum "no-violation";
      enum "violations";
    }
  }

  augment "/ncs-internal:devices/ncs-internal:device/ncs-internal:config" {
    container compliance {
      tailf:ncs-device-type "netconf";
      tailf:display-when "not(../../ncs-internal:module) or ../../ncs-internal:module[ncs-internal:name='tailf-ncs']";
      description
        "Compliance report management";
      tailf:info
        "Compliance reporting";
      container reports {
        description
          "Compliance report definitions";
        list report {
          description
            "Compliance report definition";
          key "name";
          leaf name {
            description
              "The name of a report definition";
            type string;
            tailf:info
              "Compliance report name";
          }
          tailf:action run {
            tailf:actionpoint ncsproxy {
              tailf:internal;
            }
            description
              "Run this compliance report definition and store the report output
               in a file under the state/compliance-reports directory";
            tailf:info
              "Run this compliance report";
            // NCS drop tailf:actionpoint
            input {
              leaf title {
                description
                  "The title in this report output file";
                tailf:info
                  "Report name + title in report header";
                type string;
              }
              leaf from {
                description
                  "The date and time for the lower time boundary in historical
                   analysis";
                tailf:info
                  "Audit log and check-sync events from this time";
                type yang:date-and-time;
              }
              leaf to {
                description
                  "The date and time for the upper time boundary in historical
                   analysis";
                tailf:info
                  "Audit log and check-sync events from this time";
                type yang:date-and-time;
              }
              leaf outformat {
                description
                  "The format of this report output file, and therefore also
                   the file suffix";
                type enumeration {
                  enum "text";
                  enum "xml";
                  enum "html";
                }
              }
            }
            output {
              leaf compliance-status {
                description
                  "Status indicating if any integrity violations has been
                   discovered on any device or service in this report run";
                tailf:info
                  "Any compliance violations found?";
                type compliance-status-result;
                mandatory true;
              }
              leaf id {
                description
                  "The report output file id which is key in the operational
                   data report list /compliance/report-results/report/";
                tailf:info
                  "report file id";
                type uint32;
                mandatory true;
              }
              leaf info {
                description
                  "Short description on how many devices and services where
                   covered in this report run";
                type string;
                mandatory true;
              }
              leaf location {
                description
                  "URL location for accessing the report output file";
                tailf:info
                  "File location for output";
                type inet:uri;
                mandatory true;
              }
            }
          }

          grouping devices-g {
            choice device-choice {
              mandatory true;
              case all-devices {
                leaf all-devices {
                  description
                    "Define all available devices as target for this report";
                  tailf:info
                    "Report on all devices";
                  type empty;
                }
              }
              case some-devices {
                leaf-list device-group {
                  description
                    "Define one or many device groups as target for this report";
                  tailf:info
                    "Report on specific device groups";
                  type leafref {
                    path "/ncs-internal:devices/ncs-internal:device/ncs-internal:config/ncs:devices/device-group/name" {
                      tailf:xpath-root 3;
                    }
                  }
                }
                leaf select-devices {
                  description
                    "Let the result of this XPATH expression define devices that
                     is target for this report";
                  tailf:info
                    "Report on devices selected by an XPath expression";
                  type yang:xpath1.0;
                }
                leaf-list device {
                  description
                    "Define one or many devices as target for this report";
                  tailf:info
                    "Report on specific devices";
                  type leafref {
                    path "/ncs-internal:devices/ncs-internal:device/ncs-internal:config/ncs:devices/device/name" {
                      tailf:xpath-root 3;
                    }
                  }
                }
              }
            }
          }
          container device-check {
            presence "true";
            description
              "Define the targeted devices for this compliance report definition
               and which verifications that should be performed on
               these devices";
            tailf:info
              "Report on devices";
            uses devices-g;
            leaf current-out-of-sync {
              description
                "Should a device check-sync be performed and the result added
                 to the compliance report, the default is true";
              tailf:info
                "Should current check-sync action be performed?";
              type boolean;
              default "true";
            }
            leaf historic-changes {
              description
                "Should the commit log for the defined time interval (from, to)
                 be analysed and device changes added
                 to the compliance report, the default is true";
              tailf:info
                "Include commit log events from within
                 the report interval";
              type boolean;
              default "true";
            }
            leaf historic-out-of-sync {
              description
                "Should logs be scanned for failing device check-sync events
                 for the defined time interval (from, to)
                 and found events added to the compliance report,
                 the default is true";
              tailf:info
                "Include detected devices out of sync events from within
                 the report interval";
              type boolean;
              default "true";
            }
          }
          container service-check {
            presence "true";
            description
              "Define the targeted services for this compliance report definition
               and which verifications that should be performed on
               these services";
            tailf:info
              "Report on services out of sync";
            choice service-choice {
              mandatory true;
              case all-services {
                leaf all-services {
                  description
                    "Define all available services as target for this report";
                  tailf:info
                    "Report on all services";
                  type empty;
                }
              }
              case some-services {
                leaf select-services {
                  description
                    "Let the result of this XPATH expression define services that
                     is target for this report";
                  tailf:info
                    "Report on services selected by an XPath expression";
                  type yang:xpath1.0;
                }
                leaf-list service {
                  description
                    "Define one or many services as target for this report";
                  tailf:info
                    "Report on specific services";
                  // NCS patched to string, due to LSA partial NED
                  type string;
                }
              }
            }
            leaf current-out-of-sync {
              description
                "Should a service check-sync be performed and the result added
                 to the compliance report, the default is true";
              tailf:info
                "Should current check-sync action be performed?";
              type boolean;
              default "true";
            }
            leaf historic-changes {
              description
                "Should the commit log for the defined time interval (from, to)
                 be analysed and service changes added
                 to the compliance report, the default is true";
              tailf:info
                "Include commit log events from within
                 the report interval";
              type boolean;
              default "true";
            }
            leaf historic-out-of-sync {
              description
                "Should logs be scanned for failing service check-sync events
                 for the defined time interval (from, to)
                 and found events added to the compliance report,
                 the default is true";
              tailf:info
                "Include detected services out of sync events from within
                 the report interval";
              type boolean;
              default "true";
            }
          }
          list compare-template {
            description
              "Define device templates that is used to verify current
               configuration against. If devices differ the resulting diff
               is added to the compliance report";
            tailf:info
              "Diff devices against templates";
            key "template-name device-group";
            leaf template-name {
              description
                "Template name from /devices/template";
              tailf:info
                "Diff this template";
              type leafref {
                path "/ncs-internal:devices/ncs-internal:device/ncs-internal:config/ncs:devices/ncs:template/ncs:name" {
                  tailf:xpath-root 3;
                }
              }
            }
            leaf device-group {
              description
                "Device group to apply the template on";
              tailf:info
                "Report on specific device groups";
              type leafref {
                path "/ncs-internal:devices/ncs-internal:device/ncs-internal:config/ncs:devices/device-group/name" {
                  tailf:xpath-root 3;
                }
              }
            }
            list variable {
              description
                "Set of variables to be substituted in the template";
              tailf:info
                "Variables passed to the template";
              key "name";
              leaf name {
                description
                  "Variable name from the template definition";
                tailf:info
                  "Variable name in template";
                type string;
              }
              leaf value {
                description
                  "Value for the variable";
                tailf:info
                  "Value for the variable";
                type string;
              }
            }
          }
        }
      }
      // NCS drop config false container 'report-results'
    }
  }
  augment "/ncs-internal:devices/ncs-internal:device/ncs-internal:live-status" {
    container compliance {
      tailf:ncs-device-type "netconf";
      tailf:display-when "not(../../ncs-internal:module) or ../../ncs-internal:module[ncs-internal:name='tailf-ncs'] or (../../ncs-internal:live-status-protocol[not(ncs-internal:capability)]) or (../../ncs-internal:live-status-protocol/ncs-internal:capability/ncs-internal:module[.='tailf-ncs'])";
      description
        "Compliance report management";
      tailf:info
        "Compliance reporting";
      container reports {
        description
          "Compliance report definitions";
        list report {
          description
            "Compliance report definition";
          key "name";
          leaf name {
            description
              "The name of a report definition";
            type string;
            tailf:info
              "Compliance report name";
          }
          tailf:action run {
            tailf:actionpoint ncsproxy {
              tailf:internal;
            }
            description
              "Run this compliance report definition and store the report output
               in a file under the state/compliance-reports directory";
            tailf:info
              "Run this compliance report";
            // NCS drop tailf:actionpoint
            input {
              leaf title {
                description
                  "The title in this report output file";
                tailf:info
                  "Report name + title in report header";
                type string;
              }
              leaf from {
                description
                  "The date and time for the lower time boundary in historical
                   analysis";
                tailf:info
                  "Audit log and check-sync events from this time";
                type yang:date-and-time;
              }
              leaf to {
                description
                  "The date and time for the upper time boundary in historical
                   analysis";
                tailf:info
                  "Audit log and check-sync events from this time";
                type yang:date-and-time;
              }
              leaf outformat {
                description
                  "The format of this report output file, and therefore also
                   the file suffix";
                type enumeration {
                  enum "text";
                  enum "xml";
                  enum "html";
                }
              }
            }
            output {
              leaf compliance-status {
                description
                  "Status indicating if any integrity violations has been
                   discovered on any device or service in this report run";
                tailf:info
                  "Any compliance violations found?";
                type live_ncs_compliance-status-result;
                mandatory true;
              }
              leaf id {
                description
                  "The report output file id which is key in the operational
                   data report list /compliance/report-results/report/";
                tailf:info
                  "report file id";
                type uint32;
                mandatory true;
              }
              leaf info {
                description
                  "Short description on how many devices and services where
                   covered in this report run";
                type string;
                mandatory true;
              }
              leaf location {
                description
                  "URL location for accessing the report output file";
                tailf:info
                  "File location for output";
                type inet:uri;
                mandatory true;
              }
            }
          }

          grouping devices-g {
            choice device-choice {
              // NCS drop mandatory statement
              case all-devices {
                leaf all-devices {
                  description
                    "Define all available devices as target for this report";
                  tailf:info
                    "Report on all devices";
                  type empty;
                }
              }
              case some-devices {
                leaf-list device-group {
                  description
                    "Define one or many device groups as target for this report";
                  tailf:info
                    "Report on specific device groups";
                  type leafref {
                    path "/ncs-internal:devices/ncs-internal:device/ncs-internal:live-status/ncs:devices/device-group/name" {
                      tailf:xpath-root 3;
                    }
                  }
                }
                leaf select-devices {
                  description
                    "Let the result of this XPATH expression define devices that
                     is target for this report";
                  tailf:info
                    "Report on devices selected by an XPath expression";
                  type yang:xpath1.0;
                }
                leaf-list device {
                  description
                    "Define one or many devices as target for this report";
                  tailf:info
                    "Report on specific devices";
                  type leafref {
                    path "/ncs-internal:devices/ncs-internal:device/ncs-internal:live-status/ncs:devices/device/name" {
                      tailf:xpath-root 3;
                    }
                  }
                }
              }
            }
          }
          container device-check {
            presence "true";
            description
              "Define the targeted devices for this compliance report definition
               and which verifications that should be performed on
               these devices";
            tailf:info
              "Report on devices";
            uses devices-g;
            leaf current-out-of-sync {
              description
                "Should a device check-sync be performed and the result added
                 to the compliance report, the default is true";
              tailf:info
                "Should current check-sync action be performed?";
              type boolean;
              // NCS drop default statement
            }
            leaf historic-changes {
              description
                "Should the commit log for the defined time interval (from, to)
                 be analysed and device changes added
                 to the compliance report, the default is true";
              tailf:info
                "Include commit log events from within
                 the report interval";
              type boolean;
              // NCS drop default statement
            }
            leaf historic-out-of-sync {
              description
                "Should logs be scanned for failing device check-sync events
                 for the defined time interval (from, to)
                 and found events added to the compliance report,
                 the default is true";
              tailf:info
                "Include detected devices out of sync events from within
                 the report interval";
              type boolean;
              // NCS drop default statement
            }
          }
          container service-check {
            presence "true";
            description
              "Define the targeted services for this compliance report definition
               and which verifications that should be performed on
               these services";
            tailf:info
              "Report on services out of sync";
            choice service-choice {
              // NCS drop mandatory statement
              case all-services {
                leaf all-services {
                  description
                    "Define all available services as target for this report";
                  tailf:info
                    "Report on all services";
                  type empty;
                }
              }
              case some-services {
                leaf select-services {
                  description
                    "Let the result of this XPATH expression define services that
                     is target for this report";
                  tailf:info
                    "Report on services selected by an XPath expression";
                  type yang:xpath1.0;
                }
                leaf-list service {
                  description
                    "Define one or many services as target for this report";
                  tailf:info
                    "Report on specific services";
                  // NCS patched to string, due to LSA partial NED
                  type string;
                }
              }
            }
            leaf current-out-of-sync {
              description
                "Should a service check-sync be performed and the result added
                 to the compliance report, the default is true";
              tailf:info
                "Should current check-sync action be performed?";
              type boolean;
              // NCS drop default statement
            }
            leaf historic-changes {
              description
                "Should the commit log for the defined time interval (from, to)
                 be analysed and service changes added
                 to the compliance report, the default is true";
              tailf:info
                "Include commit log events from within
                 the report interval";
              type boolean;
              // NCS drop default statement
            }
            leaf historic-out-of-sync {
              description
                "Should logs be scanned for failing service check-sync events
                 for the defined time interval (from, to)
                 and found events added to the compliance report,
                 the default is true";
              tailf:info
                "Include detected services out of sync events from within
                 the report interval";
              type boolean;
              // NCS drop default statement
            }
          }
          list compare-template {
            description
              "Define device templates that is used to verify current
               configuration against. If devices differ the resulting diff
               is added to the compliance report";
            tailf:info
              "Diff devices against templates";
            key "template-name device-group";
            leaf template-name {
              description
                "Template name from /devices/template";
              tailf:info
                "Diff this template";
              type leafref {
                path "/ncs-internal:devices/ncs-internal:device/ncs-internal:live-status/ncs:devices/ncs:template/ncs:name" {
                  tailf:xpath-root 3;
                }
              }
            }
            leaf device-group {
              description
                "Device group to apply the template on";
              tailf:info
                "Report on specific device groups";
              type leafref {
                path "/ncs-internal:devices/ncs-internal:device/ncs-internal:live-status/ncs:devices/device-group/name" {
                  tailf:xpath-root 3;
                }
              }
            }
            list variable {
              description
                "Set of variables to be substituted in the template";
              tailf:info
                "Variables passed to the template";
              key "name";
              leaf name {
                description
                  "Variable name from the template definition";
                tailf:info
                  "Variable name in template";
                type string;
              }
              leaf value {
                description
                  "Value for the variable";
                tailf:info
                  "Value for the variable";
                type string;
              }
            }
          }
        }
      }
      container report-results {
        description
          "Operational data view of compliance report output files";
        // NCS drop tailf:callpoint
        list report {
          key "id";
          leaf id {
            description
              "Report output file Id";
            // NCS drop tailf:cli-allow-range
            type uint32;
          }
          leaf name {
            description
              "Report definition in /compliance/reports/report as basis
               for this report output file";
            type string;
            tailf:non-strict-leafref {
              path "/ncs-internal:devices/ncs-internal:device/ncs-internal:live-status/compliance/reports/report/name" {
                tailf:xpath-root 3;
              }
            }
          }
          leaf title {
            description
              "The title in this report output file";
            type string;
          }
          leaf time {
            description
              "The Date and time when this report output file was produced";
            type yang:date-and-time;
          }
          leaf who {
            description
              "The name of the producer of this report output file";
            tailf:info
              "User that ran the report";
            type string;
          }
          leaf compliance-status {
            description
              "Status indicating if any integrity violations has been
               discovered on any device or service in this report run";
            tailf:info
              "Any discrepancies found";
            type live_ncs_compliance-status-result;
          }
          leaf location {
            description
              "URL location for accessing the report output file";
            tailf:info
              "Location and name of generated report";
            type inet:uri;
          }
          tailf:action remove {
            tailf:actionpoint ncsproxy {
              tailf:internal;
            }
            description
              "Remove this report result.";
            tailf:info
              "Remove this report result";
            // NCS drop tailf:actionpoint
          }
        }
      }
    }
  }
  augment "/ncs-internal:devices/ncs-internal:template/ncs-internal:ned-id/ncs-internal:config" {
    container compliance {
      description
        "Compliance report management";
      container reports {
        description
          "Compliance report definitions";
        list report {
          // NCS patched for predictable order
          ordered-by user;
          description
            "Compliance report definition";
          key "name";
          leaf name {
            description
              "The name of a report definition";
            type string;
          }

          grouping devices-g {
            choice device-choice {
              // NCS drop mandatory statement
              case all-devices {
                leaf all-devices {
                  description
                    "Define all available devices as target for this report";
                  type empty;
                }
              }
              case some-devices {
                leaf-list device-group {
                  // NCS patched for predictable order
                  ordered-by user;
                  description
                    "Define one or many device groups as target for this report";
                  type string;
                }
                leaf select-devices {
                  description
                    "Let the result of this XPATH expression define devices that
                     is target for this report";
                  type string;
                }
                leaf-list device {
                  // NCS patched for predictable order
                  ordered-by user;
                  description
                    "Define one or many devices as target for this report";
                  type string;
                }
              }
            }
          }
          container device-check {
            presence "true";
            description
              "Define the targeted devices for this compliance report definition
               and which verifications that should be performed on
               these devices";
            uses devices-g;
            leaf current-out-of-sync {
              description
                "Should a device check-sync be performed and the result added
                 to the compliance report, the default is true";
              type string;
              // NCS drop default statement
            }
            leaf historic-changes {
              description
                "Should the commit log for the defined time interval (from, to)
                 be analysed and device changes added
                 to the compliance report, the default is true";
              type string;
              // NCS drop default statement
            }
            leaf historic-out-of-sync {
              description
                "Should logs be scanned for failing device check-sync events
                 for the defined time interval (from, to)
                 and found events added to the compliance report,
                 the default is true";
              type string;
              // NCS drop default statement
            }
          }
          container service-check {
            presence "true";
            description
              "Define the targeted services for this compliance report definition
               and which verifications that should be performed on
               these services";
            choice service-choice {
              // NCS drop mandatory statement
              case all-services {
                leaf all-services {
                  description
                    "Define all available services as target for this report";
                  type empty;
                }
              }
              case some-services {
                leaf select-services {
                  description
                    "Let the result of this XPATH expression define services that
                     is target for this report";
                  type string;
                }
                leaf-list service {
                  // NCS patched for predictable order
                  ordered-by user;
                  description
                    "Define one or many services as target for this report";
                  type string;
                }
              }
            }
            leaf current-out-of-sync {
              description
                "Should a service check-sync be performed and the result added
                 to the compliance report, the default is true";
              type string;
              // NCS drop default statement
            }
            leaf historic-changes {
              description
                "Should the commit log for the defined time interval (from, to)
                 be analysed and service changes added
                 to the compliance report, the default is true";
              type string;
              // NCS drop default statement
            }
            leaf historic-out-of-sync {
              description
                "Should logs be scanned for failing service check-sync events
                 for the defined time interval (from, to)
                 and found events added to the compliance report,
                 the default is true";
              type string;
              // NCS drop default statement
            }
          }
          list compare-template {
            // NCS patched for predictable order
            ordered-by user;
            description
              "Define device templates that is used to verify current
               configuration against. If devices differ the resulting diff
               is added to the compliance report";
            key "template-name device-group";
            leaf template-name {
              description
                "Template name from /devices/template";
              type string;
            }
            leaf device-group {
              description
                "Device group to apply the template on";
              type string;
            }
            list variable {
              // NCS patched for predictable order
              ordered-by user;
              description
                "Set of variables to be substituted in the template";
              key "name";
              leaf name {
                description
                  "Variable name from the template definition";
                type string;
              }
              leaf value {
                description
                  "Value for the variable";
                type string;
              }
            }
          }
        }
      }
      // NCS drop config false container 'report-results'
    }
  }
  augment "/ncs-internal:compliance/ncs-internal:template/ncs-internal:ned-id/ncs-internal:config" {
    container compliance {
      description
        "Compliance report management";
      container reports {
        description
          "Compliance report definitions";
        list report {
          // NCS patched for predictable order
          ordered-by user;
          description
            "Compliance report definition";
          key "name";
          leaf name {
            description
              "The name of a report definition";
            type string;
          }

          grouping devices-g {
            choice device-choice {
              // NCS drop mandatory statement
              case all-devices {
                leaf all-devices {
                  description
                    "Define all available devices as target for this report";
                  type empty;
                }
              }
              case some-devices {
                leaf-list device-group {
                  // NCS patched for predictable order
                  ordered-by user;
                  description
                    "Define one or many device groups as target for this report";
                  type string;
                }
                leaf select-devices {
                  description
                    "Let the result of this XPATH expression define devices that
                     is target for this report";
                  type string;
                }
                leaf-list device {
                  // NCS patched for predictable order
                  ordered-by user;
                  description
                    "Define one or many devices as target for this report";
                  type string;
                }
              }
            }
          }
          container device-check {
            presence "true";
            description
              "Define the targeted devices for this compliance report definition
               and which verifications that should be performed on
               these devices";
            uses devices-g;
            leaf current-out-of-sync {
              description
                "Should a device check-sync be performed and the result added
                 to the compliance report, the default is true";
              type string;
              // NCS drop default statement
            }
            leaf historic-changes {
              description
                "Should the commit log for the defined time interval (from, to)
                 be analysed and device changes added
                 to the compliance report, the default is true";
              type string;
              // NCS drop default statement
            }
            leaf historic-out-of-sync {
              description
                "Should logs be scanned for failing device check-sync events
                 for the defined time interval (from, to)
                 and found events added to the compliance report,
                 the default is true";
              type string;
              // NCS drop default statement
            }
          }
          container service-check {
            presence "true";
            description
              "Define the targeted services for this compliance report definition
               and which verifications that should be performed on
               these services";
            choice service-choice {
              // NCS drop mandatory statement
              case all-services {
                leaf all-services {
                  description
                    "Define all available services as target for this report";
                  type empty;
                }
              }
              case some-services {
                leaf select-services {
                  description
                    "Let the result of this XPATH expression define services that
                     is target for this report";
                  type string;
                }
                leaf-list service {
                  // NCS patched for predictable order
                  ordered-by user;
                  description
                    "Define one or many services as target for this report";
                  type string;
                }
              }
            }
            leaf current-out-of-sync {
              description
                "Should a service check-sync be performed and the result added
                 to the compliance report, the default is true";
              type string;
              // NCS drop default statement
            }
            leaf historic-changes {
              description
                "Should the commit log for the defined time interval (from, to)
                 be analysed and service changes added
                 to the compliance report, the default is true";
              type string;
              // NCS drop default statement
            }
            leaf historic-out-of-sync {
              description
                "Should logs be scanned for failing service check-sync events
                 for the defined time interval (from, to)
                 and found events added to the compliance report,
                 the default is true";
              type string;
              // NCS drop default statement
            }
          }
          list compare-template {
            // NCS patched for predictable order
            ordered-by user;
            description
              "Define device templates that is used to verify current
               configuration against. If devices differ the resulting diff
               is added to the compliance report";
            key "template-name device-group";
            leaf template-name {
              description
                "Template name from /devices/template";
              type string;
            }
            leaf device-group {
              description
                "Device group to apply the template on";
              type string;
            }
            list variable {
              // NCS patched for predictable order
              ordered-by user;
              description
                "Set of variables to be substituted in the template";
              key "name";
              leaf name {
                description
                  "Variable name from the template definition";
                type string;
              }
              leaf value {
                description
                  "Value for the variable";
                type string;
              }
            }
          }
        }
      }
      // NCS drop config false container 'report-results'
    }
  }
}
