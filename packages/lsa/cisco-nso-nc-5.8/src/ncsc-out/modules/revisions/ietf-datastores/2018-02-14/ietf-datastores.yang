module ietf-datastores {
  // Generated by yanger -t ncs
  tailf:mount-id "cisco-nso-nc-5.8:cisco-nso-nc-5.8";
  tailf:ncs-device-type "netconf";

  yang-version 1.1;
  namespace "urn:ietf:params:xml:ns:yang:ietf-datastores";
  prefix ds;

  import tailf-common {
    prefix tailf;
  }
  import tailf-ncs-internal-mount {
    prefix ncs;
  }

  organization
    "IETF Network Modeling (NETMOD) Working Group";
  contact
    "WG Web:   <https://datatracker.ietf.org/wg/netmod/>

     WG List:  <mailto:netmod@ietf.org>

     Author:   Martin Bjorklund
               <mailto:mbj@tail-f.com>

     Author:   Juergen Schoenwaelder
               <mailto:j.schoenwaelder@jacobs-university.de>

     Author:   Phil Shafer
               <mailto:phil@juniper.net>

     Author:   Kent Watsen
               <mailto:kwatsen@juniper.net>

     Author:   Rob Wilton
               <rwilton@cisco.com>";
  description
    "This YANG module defines a set of identities for identifying
     datastores.

     Copyright (c) 2018 IETF Trust and the persons identified as
     authors of the code.  All rights reserved.

     Redistribution and use in source and binary forms, with or
     without modification, is permitted pursuant to, and subject to
     the license terms contained in, the Simplified BSD License set
     forth in Section 4.c of the IETF Trust's Legal Provisions
     Relating to IETF Documents
     (https://trustee.ietf.org/license-info).

     This version of this YANG module is part of RFC 8342
     (https://www.rfc-editor.org/info/rfc8342); see the RFC itself
     for full legal notices.";

  revision 2018-02-14 {
    description
      "Initial revision.";
    reference "RFC 8342: Network Management Datastore Architecture (NMDA)";
  }

  typedef ncs_compliance_template_datastore-ref {
    type string;
    description
      "A datastore identity reference.";
  }

  typedef ncs_template_datastore-ref {
    type string;
    description
      "A datastore identity reference.";
  }

  typedef ncs_rpc_notif_datastore-ref {
    // NCS patched to string, due to LSA partial NED
    type string;
    description
      "A datastore identity reference.";
  }

  typedef live_ncs_datastore-ref {
    // NCS patched to string, due to LSA partial NED
    type string;
    description
      "A datastore identity reference.";
  }

  typedef datastore-ref {
    // NCS patched to string, due to LSA partial NED
    type string;
    description
      "A datastore identity reference.";
  }

  identity operational {
    base datastore;
    description
      "The operational state datastore.";
  }

  identity dynamic {
    base datastore;
    description
      "Abstract base identity for dynamic configuration datastores.";
  }

  identity intended {
    base conventional;
    description
      "The intended configuration datastore.";
  }

  identity startup {
    base conventional;
    description
      "The startup configuration datastore.";
  }

  identity candidate {
    base conventional;
    description
      "The candidate configuration datastore.";
  }

  identity running {
    base conventional;
    description
      "The running configuration datastore.";
  }

  identity conventional {
    base datastore;
    description
      "Abstract base identity for conventional configuration
       datastores.";
  }

  identity datastore {
    description
      "Abstract base identity for datastore identities.";
  }
}
