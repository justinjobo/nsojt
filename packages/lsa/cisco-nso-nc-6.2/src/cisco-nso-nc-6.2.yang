module cisco-nso-nc-6.2 {
  yang-version 1.1;
  namespace "http://tail-f.com/ns/ned-id/cisco-nso-nc-6.2";
  prefix cisco-nso-nc-6.2;

  import cisco-nso-nc {
    prefix family;
  }

  identity cisco-nso-nc-6.2 {
    base family:cisco-nso-nc;
  }
}
