module tailf-ncs-kicker-extension {
  // Generated by yanger -t ncs
  tailf:mount-id "cisco-nso-nc-6.2:cisco-nso-nc-6.2";
  tailf:ncs-device-type "netconf";

  yang-version 1.1;
  namespace "http://tail-f.com/ns/ncs-kicker";
  prefix ncs-kicker;

  import ietf-yang-types {
    prefix yang;
  }
  import tailf-kicker {
    prefix kicker;
  }
  import tailf-common {
    prefix tailf;
  }
  import tailf-ncs-internal-mount {
    prefix ncs;
  }

  organization
    "Tail-f Systems";
  description
    "This submodule defines the kicker extensions that are specific
     to NCS.

     Copyright 2017-2023 Cisco Systems, Inc.
     All rights reserved.
     Permission is hereby granted to redistribute this file without
     modification.";

  revision 2023-04-13 {
    description
      "Released as part of NCS-6.1.

       Added /kickers/notification-kicker/serializer.

       Updated description of /kickers/notification-kicker/priority.";
  }
  revision 2021-09-02 {
    description
      "Released as part of NCS-5.6.

       Updated descriptions under /kickers/notification-kicker.";
  }
  revision 2019-04-09 {
    description
      "Released as part of NCS-5.1.

       Changed from submodule to module with unique namespace and prefix.
       The reason for this backward incompatible change is to be
       able to device compile the module.";
  }
  revision 2017-09-28 {
    description
      "Released as part of NCS-4.5.

       Added priority for notification kickers.";
  }
  revision 2017-03-16 {
    description
      "Initial revision, released as part of NCS-4.4.";
  }

  augment "/ncs:compliance/ncs:template/ncs:ned-id/ncs:config/kicker:kickers" {
    list notification-kicker {
      // NCS patched for predictable order
      ordered-by user;
      key "id";
      description
        "This list contains declared notification kickers.

         The notification kicker listens on notifications over
         the device subscription and for notifications of a certain type,
         identified by the notification-name container, an action is called.";
      leaf id {
        type string;
        description
          "A unique identifier for this kicker.";
      }
      leaf selector-expr {
        type string;
        // NCS drop mandatory statement
        description
          "An XPath 1.0 expression that is evaluated for all device
           notifications that are received through any subscription defined
           by /ncs:devices/device/netconf-notifications/subscription or
           /ncs:devices/device/notifications/subscription.

           The evaluation is performed using the following predefined
           variable bindings (in addition to the variable bindings defined
           in the 'variable' list):

           DEVICE            - The name of the notification emitting device.
           SUBSCRIPTION_NAME - The name of the subscription on this device
                               that did catch the notification.
           NOTIFICATION_NAME - The local name of the notification
           NOTIFICATION_NS   - The namespace of the notification

           This XPath expression is evaluated with the notification node
           as the current context and '/' as root context.
           For example, if the device model defines a notification as:

           notification mynotif {
               leaf message {
                   type string;
               }
           }

           then the current context is the notification node - 'mynotif'";
      }
      list variable {
        // NCS patched for predictable order
        ordered-by user;
        key "name";
        description
          "A list of variable bindings that will be part of the
           context when the selector expression is evaluated.";
        leaf name {
          type string;
          description
            "The name of the variable.";
        }
        leaf value {
          type string;
          // NCS drop mandatory statement
          description
            "An XPath expression that will be the value of variable
             'name'. The expression is only evaluated when used in the
             selector expression, and then it will have the
             same context as that expression.

             Note that both expressions and path expressions are
             allowed, which implies that literals must be quoted.";
        }
      }
      leaf kick-node {
        // NCS drop mandatory statement
        type string;
        description
          "When the kicker is triggered, the 'action-name' action is invoked
           on the 'kick-node' instance.

           If the 'kick-node' is given as an XPath 1.0 expression, the
           expression is evaluated with the notification that matched
           the 'selector-expr' as the context node, and the expression must
           return a node set.  The 'action-name' action is invoked on
           the nodes in this node set.";
      }
      leaf action-name {
        description
          "The action to call when a notification is received.

           The action either take the input parameters as defined by the
           'kicker:action-input-params' grouping from tailf-kicker.yang
           or else will be invoked without any parameters.";
        type string;
        // NCS drop mandatory statement
      }
      leaf priority {
        type string;
        description
          "The priority value is used to order execution of notification
           kickers that are selected and executed for the same subscription for
           the same received notification.
           First notification kickers with priority 0 are handled, then
           priority 1, priority 2 etc.
           If a kicker has a serializer value configured, only other kickers
           with the same serializer value are priority ordered relative to each
           other.";
      }
      leaf serializer {
        type string;
        description
          "A serializer value is used to ensure chronological order of
           execution of kickers that trigger at different times
           (even data kickers). If no serializer value is given, a kicker
           that is triggered at a later time might execute before a kicker
           triggered at an earlier time. Use the same serializer value for
           kickers that you want to execute in chronological order relative
           to each other.";
      }
    }
  }
  augment "/ncs:devices/ncs:template/ncs:ned-id/ncs:config/kicker:kickers" {
    list notification-kicker {
      // NCS patched for predictable order
      ordered-by user;
      key "id";
      description
        "This list contains declared notification kickers.

         The notification kicker listens on notifications over
         the device subscription and for notifications of a certain type,
         identified by the notification-name container, an action is called.";
      leaf id {
        type string;
        description
          "A unique identifier for this kicker.";
      }
      leaf selector-expr {
        type string;
        // NCS drop mandatory statement
        description
          "An XPath 1.0 expression that is evaluated for all device
           notifications that are received through any subscription defined
           by /ncs:devices/device/netconf-notifications/subscription or
           /ncs:devices/device/notifications/subscription.

           The evaluation is performed using the following predefined
           variable bindings (in addition to the variable bindings defined
           in the 'variable' list):

           DEVICE            - The name of the notification emitting device.
           SUBSCRIPTION_NAME - The name of the subscription on this device
                               that did catch the notification.
           NOTIFICATION_NAME - The local name of the notification
           NOTIFICATION_NS   - The namespace of the notification

           This XPath expression is evaluated with the notification node
           as the current context and '/' as root context.
           For example, if the device model defines a notification as:

           notification mynotif {
               leaf message {
                   type string;
               }
           }

           then the current context is the notification node - 'mynotif'";
      }
      list variable {
        // NCS patched for predictable order
        ordered-by user;
        key "name";
        description
          "A list of variable bindings that will be part of the
           context when the selector expression is evaluated.";
        leaf name {
          type string;
          description
            "The name of the variable.";
        }
        leaf value {
          type string;
          // NCS drop mandatory statement
          description
            "An XPath expression that will be the value of variable
             'name'. The expression is only evaluated when used in the
             selector expression, and then it will have the
             same context as that expression.

             Note that both expressions and path expressions are
             allowed, which implies that literals must be quoted.";
        }
      }
      leaf kick-node {
        // NCS drop mandatory statement
        type string;
        description
          "When the kicker is triggered, the 'action-name' action is invoked
           on the 'kick-node' instance.

           If the 'kick-node' is given as an XPath 1.0 expression, the
           expression is evaluated with the notification that matched
           the 'selector-expr' as the context node, and the expression must
           return a node set.  The 'action-name' action is invoked on
           the nodes in this node set.";
      }
      leaf action-name {
        description
          "The action to call when a notification is received.

           The action either take the input parameters as defined by the
           'kicker:action-input-params' grouping from tailf-kicker.yang
           or else will be invoked without any parameters.";
        type string;
        // NCS drop mandatory statement
      }
      leaf priority {
        type string;
        description
          "The priority value is used to order execution of notification
           kickers that are selected and executed for the same subscription for
           the same received notification.
           First notification kickers with priority 0 are handled, then
           priority 1, priority 2 etc.
           If a kicker has a serializer value configured, only other kickers
           with the same serializer value are priority ordered relative to each
           other.";
      }
      leaf serializer {
        type string;
        description
          "A serializer value is used to ensure chronological order of
           execution of kickers that trigger at different times
           (even data kickers). If no serializer value is given, a kicker
           that is triggered at a later time might execute before a kicker
           triggered at an earlier time. Use the same serializer value for
           kickers that you want to execute in chronological order relative
           to each other.";
      }
    }
  }
  augment "/ncs:devices/ncs:device/ncs:live-status/kicker:kickers" {
    list notification-kicker {
      tailf:ncs-device-type "netconf";
      tailf:display-when "not(../../ncs:module) or ../../ncs:module[ncs:name='tailf-ncs-kicker-extension'] or (../../ncs:live-status-protocol[not(ncs:capability)]) or (../../ncs:live-status-protocol/ncs:capability/ncs:module[.='tailf-ncs-kicker-extension'])";
      key "id";
      description
        "This list contains declared notification kickers.

         The notification kicker listens on notifications over
         the device subscription and for notifications of a certain type,
         identified by the notification-name container, an action is called.";
      leaf id {
        type string;
        description
          "A unique identifier for this kicker.";
      }
      leaf selector-expr {
        type yang:xpath1.0;
        // NCS drop mandatory statement
        description
          "An XPath 1.0 expression that is evaluated for all device
           notifications that are received through any subscription defined
           by /ncs:devices/device/netconf-notifications/subscription or
           /ncs:devices/device/notifications/subscription.

           The evaluation is performed using the following predefined
           variable bindings (in addition to the variable bindings defined
           in the 'variable' list):

           DEVICE            - The name of the notification emitting device.
           SUBSCRIPTION_NAME - The name of the subscription on this device
                               that did catch the notification.
           NOTIFICATION_NAME - The local name of the notification
           NOTIFICATION_NS   - The namespace of the notification

           This XPath expression is evaluated with the notification node
           as the current context and '/' as root context.
           For example, if the device model defines a notification as:

           notification mynotif {
               leaf message {
                   type string;
               }
           }

           then the current context is the notification node - 'mynotif'";
      }
      list variable {
        key "name";
        description
          "A list of variable bindings that will be part of the
           context when the selector expression is evaluated.";
        leaf name {
          type string;
          description
            "The name of the variable.";
        }
        leaf value {
          type yang:xpath1.0;
          // NCS drop mandatory statement
          description
            "An XPath expression that will be the value of variable
             'name'. The expression is only evaluated when used in the
             selector expression, and then it will have the
             same context as that expression.

             Note that both expressions and path expressions are
             allowed, which implies that literals must be quoted.";
        }
      }
      leaf kick-node {
        // NCS drop mandatory statement
        type union {
          // NCS patched to string, due to LSA partial NED
          type string;
          type yang:xpath1.0;
        }
        description
          "When the kicker is triggered, the 'action-name' action is invoked
           on the 'kick-node' instance.

           If the 'kick-node' is given as an XPath 1.0 expression, the
           expression is evaluated with the notification that matched
           the 'selector-expr' as the context node, and the expression must
           return a node set.  The 'action-name' action is invoked on
           the nodes in this node set.";
      }
      leaf action-name {
        description
          "The action to call when a notification is received.

           The action either take the input parameters as defined by the
           'kicker:action-input-params' grouping from tailf-kicker.yang
           or else will be invoked without any parameters.";
        type yang:yang-identifier;
        // NCS drop mandatory statement
      }
      leaf priority {
        type uint8;
        description
          "The priority value is used to order execution of notification
           kickers that are selected and executed for the same subscription for
           the same received notification.
           First notification kickers with priority 0 are handled, then
           priority 1, priority 2 etc.
           If a kicker has a serializer value configured, only other kickers
           with the same serializer value are priority ordered relative to each
           other.";
      }
      leaf serializer {
        type uint8;
        description
          "A serializer value is used to ensure chronological order of
           execution of kickers that trigger at different times
           (even data kickers). If no serializer value is given, a kicker
           that is triggered at a later time might execute before a kicker
           triggered at an earlier time. Use the same serializer value for
           kickers that you want to execute in chronological order relative
           to each other.";
      }
    }
  }
  augment "/ncs:devices/ncs:device/ncs:config/kicker:kickers" {
    list notification-kicker {
      tailf:ncs-device-type "netconf";
      tailf:display-when "not(../../ncs:module) or ../../ncs:module[ncs:name='tailf-ncs-kicker-extension']";
      key "id";
      description
        "This list contains declared notification kickers.

         The notification kicker listens on notifications over
         the device subscription and for notifications of a certain type,
         identified by the notification-name container, an action is called.";
      leaf id {
        type string;
        description
          "A unique identifier for this kicker.";
      }
      leaf selector-expr {
        type yang:xpath1.0;
        mandatory true;
        description
          "An XPath 1.0 expression that is evaluated for all device
           notifications that are received through any subscription defined
           by /ncs:devices/device/netconf-notifications/subscription or
           /ncs:devices/device/notifications/subscription.

           The evaluation is performed using the following predefined
           variable bindings (in addition to the variable bindings defined
           in the 'variable' list):

           DEVICE            - The name of the notification emitting device.
           SUBSCRIPTION_NAME - The name of the subscription on this device
                               that did catch the notification.
           NOTIFICATION_NAME - The local name of the notification
           NOTIFICATION_NS   - The namespace of the notification

           This XPath expression is evaluated with the notification node
           as the current context and '/' as root context.
           For example, if the device model defines a notification as:

           notification mynotif {
               leaf message {
                   type string;
               }
           }

           then the current context is the notification node - 'mynotif'";
      }
      list variable {
        key "name";
        description
          "A list of variable bindings that will be part of the
           context when the selector expression is evaluated.";
        leaf name {
          type string;
          description
            "The name of the variable.";
        }
        leaf value {
          type yang:xpath1.0;
          mandatory true;
          description
            "An XPath expression that will be the value of variable
             'name'. The expression is only evaluated when used in the
             selector expression, and then it will have the
             same context as that expression.

             Note that both expressions and path expressions are
             allowed, which implies that literals must be quoted.";
        }
      }
      leaf kick-node {
        mandatory true;
        type union {
          // NCS patched to string, due to LSA partial NED
          type string;
          type yang:xpath1.0;
        }
        description
          "When the kicker is triggered, the 'action-name' action is invoked
           on the 'kick-node' instance.

           If the 'kick-node' is given as an XPath 1.0 expression, the
           expression is evaluated with the notification that matched
           the 'selector-expr' as the context node, and the expression must
           return a node set.  The 'action-name' action is invoked on
           the nodes in this node set.";
      }
      leaf action-name {
        description
          "The action to call when a notification is received.

           The action either take the input parameters as defined by the
           'kicker:action-input-params' grouping from tailf-kicker.yang
           or else will be invoked without any parameters.";
        type yang:yang-identifier;
        mandatory true;
      }
      leaf priority {
        type uint8;
        description
          "The priority value is used to order execution of notification
           kickers that are selected and executed for the same subscription for
           the same received notification.
           First notification kickers with priority 0 are handled, then
           priority 1, priority 2 etc.
           If a kicker has a serializer value configured, only other kickers
           with the same serializer value are priority ordered relative to each
           other.";
      }
      leaf serializer {
        type uint8;
        description
          "A serializer value is used to ensure chronological order of
           execution of kickers that trigger at different times
           (even data kickers). If no serializer value is given, a kicker
           that is triggered at a later time might execute before a kicker
           triggered at an earlier time. Use the same serializer value for
           kickers that you want to execute in chronological order relative
           to each other.";
      }
    }
  }
}
