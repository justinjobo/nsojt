module tailf-ncs-high-availability-raft {
  // Generated by yanger -t ncs
  tailf:mount-id "cisco-nso-nc-6.2:cisco-nso-nc-6.2";
  tailf:ncs-device-type "netconf";

  yang-version 1.1;
  namespace "http://tail-f.com/ns/ncs/high-availability/raft";
  prefix haraft;

  import tailf-common {
    prefix tailf;
  }
  import ietf-yang-types {
    prefix yang;
  }
  import tailf-ncs-internal-mount {
    prefix ncs;
  }

  description
    "This module contains a collection of YANG definitions for
     managing NCS HA Raft cluster.

     Copyright 2022-2023 Cisco Systems, Inc.

     All rights reserved.
     Permission is hereby granted to redistribute this file without
     modification.";

  revision 2023-11-16 {
    description
      "Released as part of NCS-6.2.";
  }

  augment "/ncs:devices/ncs:device/ncs:config" {
    container ha-raft {
      tailf:ncs-device-type "netconf";
      tailf:display-when "not(../../ncs:module) or ../../ncs:module[ncs:name='tailf-ncs-high-availability-raft']";
      description
        "High-availability with the Raft consensus algorithm.";
      // NCS drop config false container status
      action create-cluster {
        tailf:actionpoint ncsproxy {
          tailf:internal;
        }
        description
          "Initialise an HA Raft cluster. This action should only be
           invoked once to form a new cluster when no HA Raft log
           exists.";
        // NCS drop tailf:actionpoint
        input {
          leaf-list member {
            description
              "The members of the HA Raft cluster consist of the NCS
               node where the '/ha-raft/create-cluster' action is
               invoked, which will become the leader of the cluster;
               and the members specified by the 'member' parameter.";
            type string;
          }
        }
      }
      action adjust-membership {
        tailf:actionpoint ncsproxy {
          tailf:internal;
        }
        description
          "Add or remove an HA node from the HA Raft cluster.";
        // NCS drop tailf:actionpoint
        input {
          choice command {
            mandatory true;
            leaf add-node {
              type string;
            }
            leaf remove-node {
              type string;
            }
          }
        }
      }
      action disconnect {
        tailf:actionpoint ncsproxy {
          tailf:internal;
        }
        description
          "Disconnect an HA node from all remaining nodes.";
        // NCS drop tailf:actionpoint
        input {
          leaf node {
            mandatory true;
            type string;
          }
        }
      }
      action reset {
        tailf:actionpoint ncsproxy {
          tailf:internal;
        }
        description
          "Reset the (disabled) local node to make the leader perform
           a full sync to this local node if there exists an HA Raft
           cluster. If reset is performed on the leader node, the
           node will step down from leadership and it will be synced
           by the next leader node.

           An HA Raft member will change role to 'disabled' if
           ncs.conf(5) has incompatible changes to the ncs.conf on
           the leader; a member will also change role to 'disabled'
           if there are non-recoverable failures upon opening a
           snapshot.

           See the /ha-raft/status/disable-reason leaf for reason.";
        // NCS drop tailf:actionpoint
        input {
          leaf force {
            description
              "Set force to 'true' to override reset when
               /ha-raft/status/role is not set to 'disabled'.";
            type boolean;
            default "false";
          }
        }
      }
      action handover {
        tailf:actionpoint ncsproxy {
          tailf:internal;
        }
        description
          "Handover leadership to another member of the HA Raft cluster
           or stepdown from leadership and start a new election.";
        // NCS drop tailf:actionpoint
        input {
          leaf to-member {
            description
              "The member to handover the leadership of the HA Raft
               cluster.";
            type string;
          }
        }
      }
      action read-only {
        tailf:actionpoint ncsproxy {
          tailf:internal;
        }
        description
          "Toggle read-only mode, if the mode is 'true' no configuration
           changes can occur.";
        // NCS drop tailf:actionpoint
        input {
          leaf mode {
            type boolean;
            default "true";
          }
        }
      }
    }
  }
  augment "/ncs:devices/ncs:device/ncs:live-status" {
    container ha-raft {
      tailf:ncs-device-type "netconf";
      tailf:display-when "not(../../ncs:module) or ../../ncs:module[ncs:name='tailf-ncs-high-availability-raft'] or (../../ncs:live-status-protocol[not(ncs:capability)]) or (../../ncs:live-status-protocol/ncs:capability/ncs:module[.='tailf-ncs-high-availability-raft'])";
      description
        "High-availability with the Raft consensus algorithm.";
      container status {
        description
          "Status of the HA Raft cluster.";
        // NCS drop tailf:callpoint
        leaf role {
          description
            "The role of local HA node in an HA Raft cluster.";
          type enumeration {
            enum "stalled" {
              tailf:code-name "ha-raft-stalled";
            }
            enum "candidate" {
              tailf:code-name "ha-raft-candidate";
            }
            enum "follower" {
              tailf:code-name "ha-raft-follower";
            }
            enum "leader" {
              tailf:code-name "ha-raft-leader";
            }
            enum "disabled" {
              tailf:code-name "ha-raft-disabled";
            }
          }
        }
        leaf disable-reason {
          // NCS drop when statement
          type string;
        }
        leaf leader {
          description
            "Id of current leader of the HA Raft cluster.";
          type string;
        }
        leaf-list member {
          description
            "List of the HA nodes which are HA Raft cluster members.";
          type string;
        }
        leaf-list connected-node {
          description
            "List of currently connected Distributed Erlang nodes.
             Connected nodes are the currently mesh of nodes the
             local-node has established a connection to. Form an HA
             Raft cluster with a subset of these nodes by invoking
             the /ha-raft/create-cluster or /ha-raft/adjust-membership
             actions.";
          type string;
        }
        leaf local-node {
          description
            "Id of local HA Raft node. Configured from
             /ncs-config/ha-raft/listen/node-address.";
          type string;
        }
        container certificates {
          description
            "TLS protocol certificates.";

          grouping certificate-list-leafs-grouping {
            leaf serial-number {
              description
                "The certificate's serial number.";
              type string;
            }
            leaf expiration-date {
              description
                "The certificate's expiration date.";
              type yang:date-and-time;
            }
            leaf file-path {
              description
                "The certificate's local file path.";
              type string;
            }
          }
          list certificate {
            description
              "List of loaded certificates.";
            key "serial-number";
            uses certificate-list-leafs-grouping;
          }
          list certificate-authority {
            description
              "List of loaded trusted certificate authorities.";
            key "serial-number";
            uses certificate-list-leafs-grouping;
          }
        }
        container log {
          leaf current-index {
            description
              "HA Raft log index of the HA Raft cluster leader.";
            type uint64;
          }
          leaf applied-index {
            description
              "Last HA Raft log index agreed upon via quorum.";
            type uint64;
          }
          leaf num-entries {
            type uint64;
          }

          grouping log-replications-list-leafs-grouping {
            leaf node {
              type string;
            }
            leaf state {
              description
                "Replicated HA Raft log state.";
              type enumeration {
                enum "in-sync" {
                  tailf:code-name "ha-raft-log-sync";
                }
                enum "in-process" {
                  tailf:code-name "ha-raft-log-process";
                }
                enum "requires-catchup" {
                  tailf:code-name "ha-raft-log-catchup";
                }
                enum "requires-snapshot" {
                  tailf:code-name "ha-raft-log-snapshot";
                }
              }
            }
            leaf index {
              description
                "Last replicated HA Raft log index.";
              type uint64;
            }
            leaf lag {
              description
                "Number of indices the replicated log is behind of the
                 leader node.";
              type uint64;
            }
          }
          list replications {
            // NCS drop when statement
            description
              "Replicated HA Raft log statuses of HA Raft members.";
            key "node";
            uses log-replications-list-leafs-grouping;
          }
        }
      }
      action create-cluster {
        tailf:actionpoint ncsproxy {
          tailf:internal;
        }
        description
          "Initialise an HA Raft cluster. This action should only be
           invoked once to form a new cluster when no HA Raft log
           exists.";
        // NCS drop tailf:actionpoint
        input {
          leaf-list member {
            description
              "The members of the HA Raft cluster consist of the NCS
               node where the '/ha-raft/create-cluster' action is
               invoked, which will become the leader of the cluster;
               and the members specified by the 'member' parameter.";
            type leafref {
              path "/ncs:devices/ncs:device/ncs:live-status/ha-raft/status/connected-node" {
                tailf:xpath-root 2;
              }
              require-instance false;
            }
          }
        }
      }
      action adjust-membership {
        tailf:actionpoint ncsproxy {
          tailf:internal;
        }
        description
          "Add or remove an HA node from the HA Raft cluster.";
        // NCS drop tailf:actionpoint
        input {
          choice command {
            mandatory true;
            leaf add-node {
              type leafref {
                path "/ncs:devices/ncs:device/ncs:live-status/ha-raft/status/connected-node" {
                  tailf:xpath-root 2;
                }
                require-instance false;
              }
            }
            leaf remove-node {
              type leafref {
                path "/ncs:devices/ncs:device/ncs:live-status/ha-raft/status/member" {
                  tailf:xpath-root 2;
                }
              }
            }
          }
        }
      }
      action disconnect {
        tailf:actionpoint ncsproxy {
          tailf:internal;
        }
        description
          "Disconnect an HA node from all remaining nodes.";
        // NCS drop tailf:actionpoint
        input {
          leaf node {
            mandatory true;
            type leafref {
              path "/ncs:devices/ncs:device/ncs:live-status/ha-raft/status/connected-node" {
                tailf:xpath-root 2;
              }
            }
          }
        }
      }
      action reset {
        tailf:actionpoint ncsproxy {
          tailf:internal;
        }
        description
          "Reset the (disabled) local node to make the leader perform
           a full sync to this local node if there exists an HA Raft
           cluster. If reset is performed on the leader node, the
           node will step down from leadership and it will be synced
           by the next leader node.

           An HA Raft member will change role to 'disabled' if
           ncs.conf(5) has incompatible changes to the ncs.conf on
           the leader; a member will also change role to 'disabled'
           if there are non-recoverable failures upon opening a
           snapshot.

           See the /ha-raft/status/disable-reason leaf for reason.";
        // NCS drop tailf:actionpoint
        input {
          leaf force {
            description
              "Set force to 'true' to override reset when
               /ha-raft/status/role is not set to 'disabled'.";
            type boolean;
            default "false";
          }
        }
      }
      action handover {
        tailf:actionpoint ncsproxy {
          tailf:internal;
        }
        description
          "Handover leadership to another member of the HA Raft cluster
           or stepdown from leadership and start a new election.";
        // NCS drop tailf:actionpoint
        input {
          leaf to-member {
            description
              "The member to handover the leadership of the HA Raft
               cluster.";
            type leafref {
              path "/ncs:devices/ncs:device/ncs:live-status/ha-raft/status/member" {
                tailf:xpath-root 2;
              }
            }
          }
        }
      }
      action read-only {
        tailf:actionpoint ncsproxy {
          tailf:internal;
        }
        description
          "Toggle read-only mode, if the mode is 'true' no configuration
           changes can occur.";
        // NCS drop tailf:actionpoint
        input {
          leaf mode {
            type boolean;
            default "true";
          }
        }
      }
    }
  }
  augment "/ncs:devices/ncs:template/ncs:ned-id/ncs:config" {
    container ha-raft {
      description
        "High-availability with the Raft consensus algorithm.";
      // NCS drop config false container status
    }
  }
  augment "/ncs:compliance/ncs:template/ncs:ned-id/ncs:config" {
    container ha-raft {
      description
        "High-availability with the Raft consensus algorithm.";
      // NCS drop config false container status
    }
  }
}
