module tailf-progress {
  // Generated by yanger -t ncs
  tailf:mount-id "cisco-nso-nc-6.2:cisco-nso-nc-6.2";
  tailf:ncs-device-type "netconf";

  yang-version 1.1;
  namespace "http://tail-f.com/ns/progress";
  prefix progress;

  import ietf-yang-types {
    prefix yang;
  }
  import tailf-common {
    prefix tailf;
  }
  import ietf-datastores {
    prefix ds;
  }
  import tailf-ncs-internal-mount {
    prefix ncs;
  }

  description
    "This module contains a collection of YANG definitions for
     tracing progress.

     Copyright 2018-2023 Cisco Systems, Inc.
     All rights reserved.
     Permission is hereby granted to redistribute this file without
     modification.";

  revision 2023-04-13 {
    description
      "Released as part of ConfD-8.1 / NCS-6.1.

       Moved leaf /progress/trace/event/trace-id.

       Added /progress/trace/event/span-id.

       Added /progress/trace/event/parent-span-id.

       Added /progress/trace/event/attribute.

       Added /progress/trace/event/link.

       Obsoleted /progress/trace/event/phase.

       Added grouping attributes and use this grouping in the
       /progress/trace/event list.

       Updated descriptions for /progress/trace/event/session-id and
       /progress/trace/event/transaction-id.";
  }
  revision 2021-12-17 {
    description
      "Released as part of ConfD-7.7 / NCS-5.7.

       Added /progress/trace/event/trace-id.";
  }
  revision 2020-06-25 {
    description
      "Released as part of ConfD-7.4 / NCS-5.4.

       Renamed leaf /progress/trace/event/tid to
       /progress/trace/event/transaction-id.

       Added /progress/trace/event/annotation.

       Added /progress/trace/event/database.";
  }
  revision 2018-06-14 {
    description
      "Released as part of ConfD-6.7.

       Added /progress/trace/verbosity.

       Added /progress/trace/event/timer.";
  }
  revision 2018-03-01 {
    description
      "Initial revision.";
  }

  grouping ncs_compliance_template_attributes {
    list attribute {
      // NCS patched for predictable order
      ordered-by user;
      description
        "Attributes to the progress event.";
      key "name";
      leaf name {
        type string;
      }
      leaf value {
        type string;
      }
    }
  }

  grouping ncs_compliance_template_context-grouping {
    leaf context {
      type string;
    }
  }

  grouping ncs_compliance_template_filter-input {
    container older-than {
      presence "Age specification";
      description
        "Matches the 'when' leaf in the event.";
      choice age-spec {
        case seconds {
          leaf seconds {
            type string;
          }
        }
        case minutes {
          leaf minutes {
            type string;
          }
        }
        case hours {
          leaf hours {
            type string;
          }
        }
        case days {
          leaf days {
            type string;
          }
        }
        case weeks {
          leaf weeks {
            type string;
          }
        }
      }
    }
  }

  grouping ncs_template_attributes {
    list attribute {
      // NCS patched for predictable order
      ordered-by user;
      description
        "Attributes to the progress event.";
      key "name";
      leaf name {
        type string;
      }
      leaf value {
        type string;
      }
    }
  }

  grouping ncs_template_context-grouping {
    leaf context {
      type string;
    }
  }

  grouping ncs_template_filter-input {
    container older-than {
      presence "Age specification";
      description
        "Matches the 'when' leaf in the event.";
      choice age-spec {
        case seconds {
          leaf seconds {
            type string;
          }
        }
        case minutes {
          leaf minutes {
            type string;
          }
        }
        case hours {
          leaf hours {
            type string;
          }
        }
        case days {
          leaf days {
            type string;
          }
        }
        case weeks {
          leaf weeks {
            type string;
          }
        }
      }
    }
  }

  grouping ncs_rpc_notif_attributes {
    list attribute {
      description
        "Attributes to the progress event.";
      // NCS drop tailf:display-groups
      tailf:sort-priority 1;
      key "name";
      leaf name {
        type string;
      }
      leaf value {
        // NCS drop tailf:display-groups
        type union {
          type string;
          type uint64;
          // NCS patched to string, due to LSA partial NED
          type string;
        }
      }
    }
  }

  grouping ncs_rpc_notif_context-grouping {
    leaf context {
      type union {
        type enumeration {
          enum "netconf";
          enum "cli";
          enum "webui";
          enum "snmp";
          enum "rest";
          enum "system";
        }
        type string;
      }
    }
  }

  grouping ncs_rpc_notif_filter-input {
    container older-than {
      presence "Age specification";
      description
        "Matches the 'when' leaf in the event.";
      choice age-spec {
        case seconds {
          leaf seconds {
            type uint16;
          }
        }
        case minutes {
          leaf minutes {
            type uint16;
          }
        }
        case hours {
          leaf hours {
            type uint16;
          }
        }
        case days {
          leaf days {
            type uint16;
          }
        }
        case weeks {
          leaf weeks {
            type uint16;
          }
        }
      }
    }
  }

  grouping live_ncs_attributes {
    list attribute {
      description
        "Attributes to the progress event.";
      // NCS drop tailf:display-groups
      tailf:sort-priority 1;
      key "name";
      leaf name {
        type string;
      }
      leaf value {
        // NCS drop tailf:display-groups
        type union {
          type string;
          type uint64;
          // NCS patched to string, due to LSA partial NED
          type string;
        }
      }
    }
  }

  grouping live_ncs_context-grouping {
    leaf context {
      type union {
        type enumeration {
          enum "netconf";
          enum "cli";
          enum "webui";
          enum "snmp";
          enum "rest";
          enum "system";
        }
        type string;
      }
    }
  }

  grouping live_ncs_filter-input {
    container older-than {
      presence "Age specification";
      description
        "Matches the 'when' leaf in the event.";
      choice age-spec {
        case seconds {
          leaf seconds {
            type uint16;
          }
        }
        case minutes {
          leaf minutes {
            type uint16;
          }
        }
        case hours {
          leaf hours {
            type uint16;
          }
        }
        case days {
          leaf days {
            type uint16;
          }
        }
        case weeks {
          leaf weeks {
            type uint16;
          }
        }
      }
    }
  }

  grouping attributes {
    list attribute {
      description
        "Attributes to the progress event.";
      // NCS drop tailf:display-groups
      tailf:sort-priority 1;
      key "name";
      leaf name {
        type string;
      }
      leaf value {
        // NCS drop tailf:display-groups
        type union {
          type string;
          type uint64;
          // NCS patched to string, due to LSA partial NED
          type string;
        }
      }
    }
  }

  grouping context-grouping {
    leaf context {
      type union {
        type enumeration {
          enum "netconf";
          enum "cli";
          enum "webui";
          enum "snmp";
          enum "rest";
          enum "system";
        }
        type string;
      }
    }
  }

  grouping filter-input {
    container older-than {
      presence "Age specification";
      description
        "Matches the 'when' leaf in the event.";
      choice age-spec {
        case seconds {
          leaf seconds {
            type uint16;
          }
        }
        case minutes {
          leaf minutes {
            type uint16;
          }
        }
        case hours {
          leaf hours {
            type uint16;
          }
        }
        case days {
          leaf days {
            type uint16;
          }
        }
        case weeks {
          leaf weeks {
            type uint16;
          }
        }
      }
    }
  }

  augment "/ncs:devices/ncs:device/ncs:config" {
    container progress {
      tailf:ncs-device-type "netconf";
      tailf:display-when "not(../../ncs:module) or ../../ncs:module[ncs:name='tailf-progress']";
      tailf:hidden "debug";
      list trace {
        key "name";
        leaf name {
          type string;
          description
            "A unique name for this progress trace.";
        }
        container destination {
          choice destination {
            mandatory true;
            case file {
              leaf file {
                type string;
                mandatory true;
                description
                  "Will log progress data to the given file.";
              }
              leaf format {
                type enumeration {
                  enum "csv" {
                    description
                      "Comma-separated values file defined by RFC 4180.";
                  }
                  enum "log" {
                    description
                      "Pretty printed log file with each event on a single line.";
                  }
                }
                default "csv";
              }
            }
            case oper-data {
              leaf oper-data {
                type empty;
                description
                  "Will log non-persistent operational data to the
                   ../../event list. This data can not be subscribed to.";
              }
            }
          }
        }
        leaf enabled {
          description
            "Whether the trace is enabled or not.";
          type boolean;
          default "true";
        }
        leaf max-size {
          when '../destination/oper-data' {
            tailf:xpath-root 3;
          }
          type union {
            type enumeration {
              enum "unlimited";
            }
            type uint32 {
              range "1..max";
            }
          }
          default "1000";
          description
            "Max size of the ../event list. When the maximum size
             is reached, the oldest list entry is purged.";
        }
        leaf verbosity {
          description
            "The verbosity level of the progress trace.";
          type enumeration {
            enum "normal";
            enum "verbose";
            enum "very-verbose";
            enum "debug";
          }
          default "normal";
        }
        container filter {
          description
            "If no filter is configured all transaction and
             action events will be logged.";
          leaf local-user {
            type string;
            description
              "Only log events for the specified local user.";
          }
          // NCS expand uses statement
          leaf context {
            type union {
              type enumeration {
                enum "netconf";
                enum "cli";
                enum "webui";
                enum "snmp";
                enum "rest";
                enum "system";
              }
              type string;
            }
            description
              "Only log events for the specified context.
               The context is either one of netconf, cli, webui, snmp,
               rest, system or it can be any other context string
               defined through the use of MAAPI.";
          }
        }
        tailf:action purge {
          tailf:actionpoint ncsproxy {
            tailf:internal;
          }
          // NCS drop tailf-common:display-when statement
          tailf:info
            "Remove events";
          // NCS drop tailf:actionpoint
          description
            "This action requests to delete events from the event
             list according to the supplied criteria.";
          input {
            uses filter-input;
          }
          output {
            leaf purged-events {
              type uint16;
            }
          }
        }
        // NCS drop config false list event
      }
    }
  }
  augment "/ncs:devices/ncs:device/ncs:live-status" {
    container progress {
      tailf:ncs-device-type "netconf";
      tailf:display-when "not(../../ncs:module) or ../../ncs:module[ncs:name='tailf-progress'] or (../../ncs:live-status-protocol[not(ncs:capability)]) or (../../ncs:live-status-protocol/ncs:capability/ncs:module[.='tailf-progress'])";
      tailf:hidden "debug";
      list trace {
        key "name";
        leaf name {
          type string;
          description
            "A unique name for this progress trace.";
        }
        container destination {
          choice destination {
            // NCS drop mandatory statement
            case file {
              leaf file {
                type string;
                // NCS drop mandatory statement
                description
                  "Will log progress data to the given file.";
              }
              leaf format {
                type enumeration {
                  enum "csv" {
                    description
                      "Comma-separated values file defined by RFC 4180.";
                  }
                  enum "log" {
                    description
                      "Pretty printed log file with each event on a single line.";
                  }
                }
                // NCS drop default statement
              }
            }
            case oper-data {
              leaf oper-data {
                type empty;
                description
                  "Will log non-persistent operational data to the
                   ../../event list. This data can not be subscribed to.";
              }
            }
          }
        }
        leaf enabled {
          description
            "Whether the trace is enabled or not.";
          type boolean;
          // NCS drop default statement
        }
        leaf max-size {
          // NCS drop when statement
          type union {
            type enumeration {
              enum "unlimited";
            }
            type uint32 {
              range "1..max";
            }
          }
          // NCS drop default statement
          description
            "Max size of the ../event list. When the maximum size
             is reached, the oldest list entry is purged.";
        }
        leaf verbosity {
          description
            "The verbosity level of the progress trace.";
          type enumeration {
            enum "normal";
            enum "verbose";
            enum "very-verbose";
            enum "debug";
          }
          // NCS drop default statement
        }
        container filter {
          description
            "If no filter is configured all transaction and
             action events will be logged.";
          leaf local-user {
            type string;
            description
              "Only log events for the specified local user.";
          }
          // NCS expand uses statement
          leaf context {
            type union {
              type enumeration {
                enum "netconf";
                enum "cli";
                enum "webui";
                enum "snmp";
                enum "rest";
                enum "system";
              }
              type string;
            }
            description
              "Only log events for the specified context.
               The context is either one of netconf, cli, webui, snmp,
               rest, system or it can be any other context string
               defined through the use of MAAPI.";
          }
        }
        tailf:action purge {
          tailf:actionpoint ncsproxy {
            tailf:internal;
          }
          // NCS drop tailf-common:display-when statement
          tailf:info
            "Remove events";
          // NCS drop tailf:actionpoint
          description
            "This action requests to delete events from the event
             list according to the supplied criteria.";
          input {
            uses live_ncs_filter-input;
          }
          output {
            leaf purged-events {
              type uint16;
            }
          }
        }
        list event {
          key "timestamp";
          // NCS drop tailf:callpoint
          leaf timestamp {
            // NCS drop tailf:display-groups
            type yang:date-and-time;
          }
          leaf duration {
            // NCS drop tailf:display-groups
            type decimal64 {
              fraction-digits 3;
            }
            units "seconds";
            description
              "The duration of the event in seconds.";
          }
          leaf timer {
            // NCS drop tailf:display-groups
            type decimal64 {
              fraction-digits 3;
            }
            description
              "Time difference from the first occurrence of the
               same transaction id in the list.";
          }
          leaf trace-id {
            // NCS drop tailf:display-groups
            type string {
              length "1..64";
            }
            description
              "Unique identifier for the trace.";
          }
          leaf span-id {
            // NCS drop tailf:display-groups
            type string {
              length "1..32";
            }
            description
              "Identifier for the event.";
          }
          leaf parent-span-id {
            // NCS drop tailf:display-groups
            type string {
              length "1..32";
            }
            description
              "Identifier for the parent span.";
          }
          leaf session-id {
            // NCS drop tailf:display-groups
            type uint64;
            description
              "Identifier of user session currently in use.";
          }
          leaf transaction-id {
            // NCS drop tailf:display-groups
            type uint64;
            description
              "Identifier of transaction currently in use.";
          }
          leaf datastore {
            // NCS drop tailf:display-groups
            type union {
              // NCS patched to string, due to LSA partial NED
              type string;
              // NCS patched to string, due to LSA partial NED
              type string;
            }
            description
              "The datastore of the transaction. Progress trace events
               can be emitted even for read-only datastores, for example
               when the system updates the operational state or when an
               read-only transaction is used in conjunction with the
               invocation of an action.";
          }
          // NCS expand uses statement
          leaf context {
            type union {
              type enumeration {
                enum "netconf";
                enum "cli";
                enum "webui";
                enum "snmp";
                enum "rest";
                enum "system";
              }
              type string;
            }
            // NCS drop tailf:display-groups
            description
              "The context is either one of netconf, cli, webui, snmp,
               rest, system or it can be any other context string
               defined through the use of MAAPI.";
          }
          leaf subsystem {
            // NCS drop tailf:display-groups
            type string;
            description
              "The name of the subsystem that generated the event.";
          }
          leaf phase {
            status obsolete;
            // NCS drop tailf:display-groups
            type enumeration {
              enum "validate" {
                tailf:code-name "transaction_validate";
              }
              enum "write-start" {
                tailf:code-name "transaction_write_start";
              }
              enum "prepare" {
                tailf:code-name "transaction_prepare";
              }
              enum "commit" {
                tailf:code-name "transaction_commit";
              }
              enum "abort" {
                tailf:code-name "transaction_abort";
              }
            }
            description
              "The phase of the transaction.";
          }
          leaf message {
            // NCS drop tailf:display-groups
            tailf:sort-priority 1;
            type string;
            description
              "Progress event message.";
          }
          leaf annotation {
            // NCS drop tailf:display-groups
            tailf:sort-priority 1;
            type string;
            description
              "Metadata about the event, indicating error, explains
               latency or shows result etc.";
          }
          uses live_ncs_attributes;
          list link {
            description
              "References to other progress events.";
            // NCS drop tailf:display-groups
            tailf:sort-priority 1;
            key "trace-id span-id";
            leaf trace-id {
              type string {
                length "1..64";
              }
            }
            leaf span-id {
              type string {
                length "1..32";
              }
            }
          }
        }
      }
    }
  }
  augment "/ncs:devices/ncs:template/ncs:ned-id/ncs:config" {
    container progress {
      tailf:hidden "debug";
      list trace {
        // NCS patched for predictable order
        ordered-by user;
        key "name";
        leaf name {
          type string;
          description
            "A unique name for this progress trace.";
        }
        container destination {
          choice destination {
            // NCS drop mandatory statement
            case file {
              leaf file {
                type string;
                // NCS drop mandatory statement
                description
                  "Will log progress data to the given file.";
              }
              leaf format {
                type string;
                // NCS drop default statement
              }
            }
            case oper-data {
              leaf oper-data {
                type empty;
                description
                  "Will log non-persistent operational data to the
                   ../../event list. This data can not be subscribed to.";
              }
            }
          }
        }
        leaf enabled {
          description
            "Whether the trace is enabled or not.";
          type string;
          // NCS drop default statement
        }
        leaf max-size {
          // NCS drop when statement
          type string;
          // NCS drop default statement
          description
            "Max size of the ../event list. When the maximum size
             is reached, the oldest list entry is purged.";
        }
        leaf verbosity {
          description
            "The verbosity level of the progress trace.";
          type string;
          // NCS drop default statement
        }
        container filter {
          description
            "If no filter is configured all transaction and
             action events will be logged.";
          leaf local-user {
            type string;
            description
              "Only log events for the specified local user.";
          }
          // NCS expand uses statement
          leaf context {
            type string;
            description
              "Only log events for the specified context.
               The context is either one of netconf, cli, webui, snmp,
               rest, system or it can be any other context string
               defined through the use of MAAPI.";
          }
        }
        // NCS drop config false list event
      }
    }
  }
  augment "/ncs:compliance/ncs:template/ncs:ned-id/ncs:config" {
    container progress {
      tailf:hidden "debug";
      list trace {
        // NCS patched for predictable order
        ordered-by user;
        key "name";
        leaf name {
          type string;
          description
            "A unique name for this progress trace.";
        }
        container destination {
          choice destination {
            // NCS drop mandatory statement
            case file {
              leaf file {
                type string;
                // NCS drop mandatory statement
                description
                  "Will log progress data to the given file.";
              }
              leaf format {
                type string;
                // NCS drop default statement
              }
            }
            case oper-data {
              leaf oper-data {
                type empty;
                description
                  "Will log non-persistent operational data to the
                   ../../event list. This data can not be subscribed to.";
              }
            }
          }
        }
        leaf enabled {
          description
            "Whether the trace is enabled or not.";
          type string;
          // NCS drop default statement
        }
        leaf max-size {
          // NCS drop when statement
          type string;
          // NCS drop default statement
          description
            "Max size of the ../event list. When the maximum size
             is reached, the oldest list entry is purged.";
        }
        leaf verbosity {
          description
            "The verbosity level of the progress trace.";
          type string;
          // NCS drop default statement
        }
        container filter {
          description
            "If no filter is configured all transaction and
             action events will be logged.";
          leaf local-user {
            type string;
            description
              "Only log events for the specified local user.";
          }
          // NCS expand uses statement
          leaf context {
            type string;
            description
              "Only log events for the specified context.
               The context is either one of netconf, cli, webui, snmp,
               rest, system or it can be any other context string
               defined through the use of MAAPI.";
          }
        }
        // NCS drop config false list event
      }
    }
  }

  identity pre-commit-running {
    description
      "The pre-commit-running configuration datastore.";
    base datastore;
  }

  identity datastore {
    description
      "Abstract base identity for datastore identities.";
  }
}
