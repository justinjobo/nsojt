module tailf-ncs-ned {
  // Generated by yanger -t ncs
  tailf:mount-id "cisco-nso-nc-6.2:cisco-nso-nc-6.2";
  tailf:ncs-device-type "netconf";

  namespace "http://tail-f.com/ns/ncs-ned";
  prefix ned;

  import tailf-common {
    prefix tailf;
  }
  import tailf-ncs-internal-mount {
    prefix ncs;
  }

  organization
    "Tail-f Systems";
  description
    "This module defines the Tail-f NCS NED base identities.

     Copyright 2011-2021 Cisco Systems, Inc.
     All rights reserved.
     Permission is hereby granted to redistribute this file without
     modification.";

  revision 2021-09-02 {
    description
      "Released as part of NCS-5.6.

       Added identity 'generic-ned-notification-id'.

       Added idenity 'cli-ned-notification-id'.";
  }
  revision 2019-04-09 {
    description
      "Released as part of NCS-5.1.

       Added 'ned-id' as base to all protocol specific ned ids.";
  }
  revision 2016-11-24 {
    description
      "Released as part of NCS-4.3.

       Added base identity for NETCONF devices.
       Added identity lsa-netconf";
  }
  revision 2011-06-01 {
    description
      "Released as part of NCS-1.6.";
  }

  identity snmp {
    base snmp-ned-id;
    description
      "Default identity for an SNMP device.";
  }

  identity lsa-netconf {
    base netconf-ned-id;
    description
      "Base identity for LSA nodes.";
  }

  identity netconf {
    base netconf-ned-id;
    description
      "Default identity for a netconf device.";
  }

  identity cli-ned-notification-id {
    base cli-ned-id;
    tailf:abstract;
    description
      "Special internal id for CLI NEDs with notification capability.";
  }

  identity generic-ned-notification-id {
    base generic-ned-id;
    tailf:abstract;
    description
      "Special internal id for generic NEDs with notification capability.";
  }

  identity rfc5277-id {
    base netconf-ned-id;
    tailf:abstract;
    description
      "Special internal id for the data model in RFC 5277.";
  }

  identity snmp-ned-id {
    base ned-id;
    tailf:abstract;
    description
      "Base identity for SNMP NEDs.

       Note that currently there is no way to actually set a ned-id
       for SNMP devices.";
  }

  identity cli-ned-id {
    base ned-id;
    tailf:abstract;
    description
      "Base identity for CLI NEDs.";
  }

  identity generic-ned-id {
    base ned-id;
    tailf:abstract;
    description
      "Base identity for generic NEDs.";
  }

  identity netconf-ned-id {
    base ned-id;
    tailf:abstract;
    description
      "Base identity for NETCONF NEDs.";
  }

  identity ned-id {
    description
      "Base identity for Tail-f NEDs.";
  }
}
