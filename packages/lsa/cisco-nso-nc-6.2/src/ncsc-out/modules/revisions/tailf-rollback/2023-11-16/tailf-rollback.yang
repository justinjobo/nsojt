module tailf-rollback {
  // Generated by yanger -t ncs
  tailf:mount-id "cisco-nso-nc-6.2:cisco-nso-nc-6.2";
  tailf:ncs-device-type "netconf";

  yang-version 1.1;
  namespace "http://tail-f.com/ns/rollback";
  prefix rollback;

  import ietf-yang-types {
    prefix yang;
  }
  import tailf-common {
    prefix tailf;
  }
  import tailf-ncs-internal-mount {
    prefix ncs;
  }

  organization
    "Tail-f Systems";
  description
    "This module defines a data model for rollback file handling.

     Copyright 2016-2023 Cisco Systems, Inc.
     All rights reserved.
     Permission is hereby granted to redistribute this file without
     modification.";

  revision 2023-11-16 {
    description
      "Released as part of ConfD-8.2 / NCS-6.2.

       Added leaf-list exclude to input of apply-rollback-file action.";
  }
  revision 2023-04-13 {
    description
      "Released as part of ConfD-8.1 / NCS-6.1.

       Exported this module to all interfaces.

       Added remote augment of /ypstatus/yang-patch-status/global-status/ok.";
  }
  revision 2020-09-02 {
    description
      "Released as part of ConfD-7.6 / NCS-5.6.

       Added 'label' and 'comment' input leafs to apply-rollback-file action.";
  }
  revision 2020-06-25 {
    description
      "Released as part of ConfD-7.4 / NCS-5.4.

       Moved grouping rollback-reference to module top level.

       Add grouping rollback-commit-result.";
  }
  revision 2018-01-12 {
    description
      "Released as part of ConfD-6.4.5 / NCS-4.4.5.

       Exported to NETCONF and maapi.

       Made the input id parameter mandatory (as it already was, but
       not explicitly).

       Added selective and path input parameters to
       apply-rollback-file action.";
  }
  revision 2016-09-15 {
    description
      "Initial release.";
  }

  grouping ncs_compliance_template_rollback-reference {
    choice rollback {
      // NCS drop mandatory statement
      leaf id {
        description
          "The identifier of the rollback file.";
        type string;
      }
      leaf fixed-number {
        description
          "The fixed-number of the rollback file.";
        type string;
      }
    }
  }

  grouping ncs_compliance_template_rollback-commit-result {
    container rollback {
      presence "Rollback reference available in the result.";
      uses ncs_compliance_template_rollback-reference;
    }
  }

  grouping ncs_template_rollback-reference {
    choice rollback {
      // NCS drop mandatory statement
      leaf id {
        description
          "The identifier of the rollback file.";
        type string;
      }
      leaf fixed-number {
        description
          "The fixed-number of the rollback file.";
        type string;
      }
    }
  }

  grouping ncs_template_rollback-commit-result {
    container rollback {
      presence "Rollback reference available in the result.";
      uses ncs_template_rollback-reference;
    }
  }

  grouping ncs_rpc_notif_rollback-reference {
    choice rollback {
      mandatory true;
      leaf id {
        description
          "The identifier of the rollback file.";
        type string;
      }
      leaf fixed-number {
        description
          "The fixed-number of the rollback file.";
        type string;
      }
    }
  }

  grouping ncs_rpc_notif_rollback-commit-result {
    container rollback {
      presence "Rollback reference available in the result.";
      uses ncs_rpc_notif_rollback-reference;
    }
  }

  grouping live_ncs_rollback-reference {
    choice rollback {
      // NCS drop mandatory statement
      leaf id {
        description
          "The identifier of the rollback file.";
        type leafref {
          path "/ncs:devices/ncs:device/ncs:live-status/rollback:rollback-files/rollback:file/rollback:id" {
            tailf:xpath-root 3;
          }
        }
      }
      leaf fixed-number {
        description
          "The fixed-number of the rollback file.";
        type leafref {
          path "/ncs:devices/ncs:device/ncs:live-status/rollback:rollback-files/rollback:file/rollback:fixed-number" {
            tailf:xpath-root 3;
          }
        }
      }
    }
  }

  grouping live_ncs_rollback-commit-result {
    container rollback {
      presence "Rollback reference available in the result.";
      uses live_ncs_rollback-reference;
    }
  }

  grouping rollback-reference {
    choice rollback {
      mandatory true;
      leaf id {
        description
          "The identifier of the rollback file.";
        type leafref {
          path "/ncs:devices/ncs:device/ncs:live-status/rollback:rollback-files/rollback:file/rollback:id" {
            tailf:xpath-root 2;
          }
        }
      }
      leaf fixed-number {
        description
          "The fixed-number of the rollback file.";
        type leafref {
          path "/ncs:devices/ncs:device/ncs:live-status/rollback:rollback-files/rollback:file/rollback:fixed-number" {
            tailf:xpath-root 2;
          }
        }
      }
    }
  }

  grouping rollback-commit-result {
    container rollback {
      presence "Rollback reference available in the result.";
      uses rollback-reference;
    }
  }

  augment "/ncs:devices/ncs:device/ncs:config" {
    // NCS drop config false container 'rollback-files'
  }
  augment "/ncs:devices/ncs:device/ncs:live-status" {
    container rollback-files {
      tailf:ncs-device-type "netconf";
      tailf:display-when "not(../../ncs:module) or ../../ncs:module[ncs:name='tailf-rollback'] or (../../ncs:live-status-protocol[not(ncs:capability)]) or (../../ncs:live-status-protocol/ncs:capability/ncs:module[.='tailf-rollback'])";
      tailf:info
        "Rollback file handling";
      // NCS drop tailf:callpoint
      list file {
        key "id";
        description
          "Rollback file information.";
        leaf id {
          type uint32;
          description
            "Identifier for a rollback file.";
        }
        leaf name {
          type string;
          description
            "Filename of the rollback file.";
        }
        leaf fixed-number {
          type uint64;
          description
            "The number of this rollback files. This number doesn't
             change and can be used as input to the get- and apply-
             actions defined in this module.";
        }
        leaf creator {
          type string;
          description
            "The user which caused the rollback file to be created.";
        }
        leaf date {
          type string;
          description
            "Date for the creation of the rollback file.";
        }
        leaf via {
          type string;
          description
            "What interface was used when the rollback file was created.";
        }
        leaf label {
          type string;
          description
            "A label.";
        }
        leaf comment {
          type string;
          description
            "A comment.";
        }
      }
      action get-rollback-file {
        tailf:actionpoint ncsproxy {
          tailf:internal;
        }
        description
          "Get the content of a specific rollback file.";
        // NCS drop tailf:actionpoint
        input {
          uses live_ncs_rollback-reference;
        }
        output {
          leaf content {
            type string;
          }
        }
      }
      action apply-rollback-file {
        tailf:actionpoint ncsproxy {
          tailf:internal;
        }
        description
          "Apply a specific rollback file.";
        // NCS drop tailf:actionpoint
        input {
          uses live_ncs_rollback-reference;
          leaf selective {
            type empty;
            description
              "Only apply the changes in this particular rollback file.";
          }
          leaf path {
            type yang:xpath1.0;
            description
              "Only apply changes for the sub tree restricted by this path.";
          }
          leaf-list exclude {
            type yang:xpath1.0;
            description
              "Exclude specified paths from any applied changes.";
            must 'not("../path") or "../path" = ""' {
              tailf:xpath-root 3;
              error-message "Cannot be used when a restricted path is specified";
            }
          }
          leaf label {
            type leafref {
              path "/ncs:devices/ncs:device/ncs:live-status/rollback:rollback-files/rollback:file/rollback:label" {
                tailf:xpath-root 3;
              }
            }
          }
          leaf comment {
            type leafref {
              path "/ncs:devices/ncs:device/ncs:live-status/rollback:rollback-files/rollback:file/rollback:comment" {
                tailf:xpath-root 3;
              }
            }
          }
        }
      }
    }
  }
  augment "/ncs:devices/ncs:template/ncs:ned-id/ncs:config" {
    // NCS drop config false container 'rollback-files'
  }
  augment "/ncs:compliance/ncs:template/ncs:ned-id/ncs:config" {
    // NCS drop config false container 'rollback-files'
  }
}
