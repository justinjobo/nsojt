module tailf-ncs-progress {
  namespace "http://tail-f.com/ns/ncs-progress";
  prefix ncs-progress;

  import ietf-yang-types {
    prefix yang;
  }

  import tailf-progress {
    prefix progress;
  }

  import tailf-common {
    prefix tailf;
  }

  import tailf-ncs {
    prefix ncs;
  }

  description
    "This module contains a collection of YANG definitions for
     tracing progress in NCS.

     Copyright 2018-2022 Cisco Systems, Inc.
     All rights reserved.
     Permission is hereby granted to redistribute this file without
     modification.";

  revision 2023-04-04 {
    description
      "Released as part of ConfD-8.1 / NCS-6.1.

       Obsoleted all leaves augmented into
       /progress:progress/trace/event.";
  }

  revision 2022-09-29 {
    description
      "Released as part of NCS-6.0.

       Non-backwards-compatible changes have been introduced.

       Added enum 'delete' to
       /progress/trace/event/service-phase.

       Removed enum 'pre-lock-create' from
       /progress/trace/event/service-phase.

       Removed enum 'show-stats' and 'show-stats-list'
       from /progress/trace/event/device-phase.

       Added enum 'show-stats-filter' to
       /progress/trace/event/device-phase.";
  }

  revision 2021-09-02 {
    description
      "Released as part of NCS-5.6.

       Added /progress/trace/event/package.

       Added enum 'create-subscription' to
       /progress/trace/event/device-phase.";
  }

  revision 2020-06-25 {
    description
      "Released as part of NCS-5.4.

       Added /progress/trace/debug.";
  }

  revision 2019-06-27 {
    description
      "Released as part of NCS-5.2.

       Added /progress/trace/event/package.

       Added enum 'show-offline', 'show-stats', 'show-stats-list',
       'is-alive', 'keep-alive', 'reconnect', and 'cmd' to
       /progress/trace/event/device-phase.";
  }

  revision 2018-11-12 {
    description
      "Released as part of NCS-4.7.2.

       Made leaf /progress/trace/event/service to not require instance.";
  }

  revision 2018-06-21 {
    description
      "Released as part of NCS-4.7.

       Added display-groups to some nodes.";
  }

  revision 2018-03-01 {
    description
      "Released as part of NCS-4.6.

       Initial revision.";
  }

  augment "/progress:progress/progress:trace" {
    leaf-list debug {
      description
        "Additional debug tracing. These are consciously left out of the
         normal debug level due to the high amount of output.
         Use with care.";
      type enumeration {
        enum xpath {
          description
            "Detailed output from the XPath evaluator.";
        }
        enum kicker {
          description
            "Detailed output from data kicker evaluation.";
        }
        enum subscriber {
          description
            "Detailed output from CDB subscribers.";
        }
      }
    }
  }

  augment "/progress:progress/progress:trace/progress:filter" {
    choice object {
      case service {
        leaf all-services {
          type empty;
          description
            "Only log events for services.";
        }
        leaf service-type {
          type tailf:node-instance-identifier;
          tailf:cli-completion-actionpoint "servicepoints";
          description
            "Only log events for the specified service type.";
        }
      }
      case device {
        choice device-choice {
          leaf all-devices {
            type empty;
            description
              "Only log events for devices.";
          }
          leaf device-group {
            type string;
            tailf:non-strict-leafref {
              path "/ncs:devices/ncs:device-group/ncs:name";
            }
            description
              "Only log events for devices in this group.";
          }
          leaf-list device {
            type string;
            tailf:non-strict-leafref {
              path "/ncs:devices/ncs:device/ncs:name";
            }
            description
              "Only log events for the specified device(s).";
          }
        }
      }
    }
  }

  augment "/progress:progress/progress:trace/progress:event" {
    leaf service {
      status obsolete;
      tailf:display-groups "obsolete";
      type instance-identifier {
        require-instance false;
      }
      description
        "The invoked service instance.

         This leaf has been obsoleted. Use attribute list instead.";
    }
    leaf service-phase {
      status obsolete;
      tailf:display-groups "obsolete";
      type enumeration {
        enum pre-modification;
        enum delete;
        enum create;
        enum post-modification;
      }
      description
        "The callback phase of the invoked service instance.

         This leaf has been obsoleted. Use attribute list instead.";
    }
    leaf commit-queue-id {
      status obsolete;
      tailf:display-groups "obsolete";
      type uint64;
      description
        "The commit queue item id.

         This leaf has been obsoleted. Use attribute list instead.";
    }
    leaf node {
      status obsolete;
      tailf:display-groups "obsolete";
      type ncs:node-name;
      tailf:non-strict-leafref {
        path "/ncs:cluster/ncs:remote-node/ncs:name";
      }
      description
        "The remote cluster node used.

         This leaf has been obsoleted. Use attribute list instead.";
    }
    leaf device {
      status obsolete;
      tailf:display-groups "obsolete";
      type string;
      tailf:non-strict-leafref {
        path "/ncs:devices/ncs:device/ncs:name";
      }
      description
        "The device used.

         This leaf has been obsoleted. Use attribute list instead.";
    }
    leaf device-phase {
      status obsolete;
      tailf:display-groups "obsolete";
      type enumeration {
        enum noconnect;
        enum connect;
        enum initialize;
        enum uninitialize;
        enum prepare;
        enum abort;
        enum commit;
        enum revert;
        enum persist;
        enum close;
        enum get-trans-id;
        enum show;
        enum show-partial;
        enum scp;
        enum show-offline;
        enum show-stats-path {
          value 17;
        }
        enum is-alive;
        enum keep-alive;
        enum reconnect;
        enum cmd;
        enum create-subscription;
        enum show-stats-filter;
      }
      description
        "The device communication phase.

         This leaf has been obsoleted. Use attribute list instead.";
    }
    leaf package {
      status obsolete;
      tailf:display-groups "obsolete";
      type string;
      description
        "The package the event was reported from.

         This leaf has been obsoleted. Use attribute list instead.";
    }
  }
}
