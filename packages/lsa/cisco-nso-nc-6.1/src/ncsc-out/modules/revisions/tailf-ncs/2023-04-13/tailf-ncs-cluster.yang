submodule tailf-ncs-cluster {
  // Generated by yanger -t ncs
  tailf:mount-id "cisco-nso-nc-6.1:cisco-nso-nc-6.1";

  yang-version 1.1;
  belongs-to tailf-ncs {
    prefix ncs;
  }

  import ietf-inet-types {
    prefix inet;
  }
  import ietf-yang-types {
    prefix yang;
  }
  import tailf-common {
    prefix tailf;
  }
  include tailf-ncs-common;
  include tailf-ncs-ssh;
  import tailf-ncs-internal-mount {
    prefix ncs-internal;
  }

  organization
    "Tail-f Systems";
  description
    "This submodule contains configuration items for NCS cluster settings.

     Copyright 2013-2021 Cisco Systems, Inc.
     All rights reserved.
     Permission is hereby granted to redistribute this file without
     modification.";

  revision 2021-09-02 {
    description
      "Released as part of NCS-5.6.

       Non-backwards-compatible changes have been introduced.

       Removed /cluster/caching and /cluster/remote-node/device.

       Added /cluster/remote-node/ssh-algorithms.";
  }
  revision 2019-11-28 {
    description
      "Released as part of NCS-5.3.

       Changed /cluster/authgroup/default-map/remote-password and
       /cluster/authgroup/umap/remote-password from
       tailf:aes-cfb-128-encrypted-string to
       tailf:aes-256-cfb-128-encrypted-string.

       Added /cluster/remote-node/trace-output.";
  }
  revision 2018-03-01 {
    description
      "Released as part of NCS-4.6.

       Added 'must' expressions for /cluster/commit-queue/enabled and
       /cluster/device-notifications/enabled.";
  }
  revision 2017-09-28 {
    description
      "Released as part of NCS-4.5.

       Changed /cluster/remote-node/notifications/stream/sequence-no from
       int32 to uint64.";
  }
  revision 2017-03-16 {
    description
      "Released as part of NCS-4.4.

       Added range to all config leafs specifying time.";
  }
  revision 2015-11-24 {
    description
      "Released as part of NCS-4.1.

       Added /cluster/device-notifications/enabled.";
  }
  revision 2015-10-02 {
    description
      "Released as part of NCS-4.0.2.

       Added /cluster/global-settings/timeouts/connect-timeout.

       Added /cluster/global-settings/ssh-keep-alive/interval.

       Added /cluster/global-settings/ssh-keep-alive/count.";
  }
  revision 2015-05-05 {
    description
      "Released as part of NCS-3.4.1.

       Added /cluster/global-settings/caching.";
  }
  revision 2015-03-19 {
    description
      "Released as part of NCS-3.4.

       Removed config false leaf /cluster/enabled.

       Added /cluster/remote-node/notifications/stream, and moved
         /cluster/remote-node/notifications/status into this list.";
  }
  revision 2014-11-19 {
    description
      "Released as part of NCS-3.3.

       Added /cluster/remote-node/cq-subscription-authgroup. This item contains
       the authgroup for NETCONF notifications needed by commit-queues in a
       cluster environment.

       Added /cluster/commit-queue.

       Added /cluster/remote-node/username.

       Added /cluster/remote-node/notifications";
  }
  revision 2014-06-30 {
    description
      "Released as part of NCS-3.2.

       Added use of grouping ssh-host-keys from submodule tailf-ncs-ssh,
       creating /cluster/remote-node/ssh.

       Added use of grouping public-key-auth from submodule tailf-ncs-ssh
       in remote-user-remote-auth grouping, creating
       /cluster/authgroup/default-map/public-key and
       /cluster/authgroup/umap/public-key.";
  }
  revision 2013-11-12 {
    description
      "Initial revision, released as part of NCS-3.0.";
  }

  typedef ncs_compliance_template_node-name {
    type string;
  }

  typedef ncs_template_node-name {
    type string;
  }

  typedef ncs_rpc_notif_node-name {
    type inet:domain-name;
  }

  typedef live_ncs_node-name {
    type inet:domain-name;
  }

  typedef node-name {
    type inet:domain-name;
  }

  augment "/ncs-internal:devices/ncs-internal:device/ncs-internal:config" {
    container cluster {
      tailf:ncs-device-type "netconf";
      tailf:display-when "not(../../ncs-internal:module) or ../../ncs-internal:module[ncs-internal:name='tailf-ncs']";
      tailf:info
        "Cluster configuration";
      container global-settings {
        tailf:info
          "Global settings for all remote nodes";
        container timeouts {
          description
            "Timeouts used when communicating with a remote node in the cluster.";
          leaf connect-timeout {
            tailf:info
              "Timeout in seconds for new connections";
            type uint32 {
              range "1..4294967";
            }
            default "20";
            units "seconds";
            description
              "The timeout in seconds for new connections to a remote node.";
          }
        }
        container ssh-keep-alive {
          description
            "Controls SSH keep alive settings when communicating from this
             node to remote devices.";
          tailf:info
            "Controls SSH keep alive settings";
          leaf interval {
            type uint32 {
              range "0..4294967";
            }
            default "20";
            units "seconds";
            description
              "Seconds between SSH keep alive activity.";
          }
          leaf count {
            type uint8;
            default "2";
            description
              "Number of intervals to fail before failing the connection.";
          }
        }
      }
      list remote-node {
        tailf:info
          "List of configured remote nodes";
        key "name";
        leaf name {
          tailf:info
            "Name of remote node";
          tailf:cli-allow-range;
          type node-name;
        }
        leaf address {
          tailf:info
            "Address of remote node (defaults to name)";
          type inet:host;
          description
            "Address of remote node. Unless set the node-name will be
             interpreted as the hostname";
        }
        leaf port {
          tailf:info
            "Port number of remote node";
          type inet:port-number;
          default "830";
          description
            "NETCONF port of remote node.";
        }
        uses ssh-connection-config;
        container ssh-algorithms {
          description
            "Supported (allowed) algorithms that should be used during
             SSH algorithm negotiations.";
          // NCS expand uses statement
          leaf-list public-key {
            description
              "Supported public key algorithms. Only the ones supported by the
               underlying SSH implementation will be used.";
            type ssh-public-key-algorithm;
            ordered-by user;
            default "ssh-ed25519";
            default "ecdsa-sha2-nistp256";
            default "ecdsa-sha2-nistp384";
            default "ecdsa-sha2-nistp521";
            default "rsa-sha2-512";
            default "rsa-sha2-256";
          }
          leaf-list kex {
            description
              "Supported key exchange algorithms. Only the ones supported
               by the underlying SSH implementation will be used.";
            ordered-by user;
            type ssh-kex-algorithm;
            default "curve25519-sha256";
            default "curve25519-sha256@libssh.org";
            default "ecdh-sha2-nistp256";
            default "ecdh-sha2-nistp384";
            default "curve448-sha512";
            default "ecdh-sha2-nistp521";
            default "diffie-hellman-group15-sha512";
            default "diffie-hellman-group16-sha512";
            default "diffie-hellman-group14-sha256";
            default "diffie-hellman-group14-sha1";
          }
          leaf-list mac {
            description
              "Supported MAC algorithms. Only the ones supported by the
               underlying SSH implementation will be used.";
            ordered-by user;
            type ssh-mac-algorithm;
            default "AEAD_AES_128_GCM";
            default "AEAD_AES_256_GCM";
            default "hmac-sha2-512-etm@openssh.com";
            default "hmac-sha2-256-etm@openssh.com";
            default "hmac-sha2-512";
            default "hmac-sha2-256";
            default "hmac-sha1";
          }
          leaf-list cipher {
            description
              "Supported cipher algorithms. Only the ones supported by the
               underlying SSH implementation will be used.";
            ordered-by user;
            type ssh-cipher-algorithm;
            default "aes128-gcm@openssh.com";
            default "AEAD_AES_128_GCM";
            default "chacha20-poly1305@openssh.com";
            default "aes256-gcm@openssh.com";
            default "AEAD_AES_256_GCM";
            default "aes128-ctr";
            default "aes192-ctr";
            default "aes256-ctr";
          }
          leaf-list compression {
            description
              "Supported compression algorithms. Only the ones supported by the
               underlying SSH implementation will be used.";
            ordered-by user;
            type ssh-compression-algorithm;
            default "none";
            default "zlib";
            default "zlib@openssh.com";
          }
          container dh-group {
            description
              "Range of allowed group size the client will request during
                        a \"diffie-hellman-group-exchange\". The range will be the
                        intersection of these values and what the server supports";
            leaf min-size {
              must '. <= ../max-size' {
                tailf:xpath-root 3;
              }
              type dh-group-size-type;
              description
                "Minimal size of p in bits.";
              default "1024";
            }
            leaf preferred-size {
              must '. <= ../max-size and . >= ../min-size' {
                tailf:xpath-root 3;
              }
              type dh-group-size-type;
              description
                "Preferred size of p in bits.";
              default "2048";
            }
            leaf max-size {
              type dh-group-size-type;
              description
                "Maximal size of p in bits.";
              default "8192";
            }
          }
        }
        leaf authgroup {
          tailf:info
            "Authentication credentials for the node";
          type leafref {
            path "/ncs-internal:devices/ncs-internal:device/ncs-internal:config/cluster/authgroup/name" {
              tailf:xpath-root 3;
            }
          }
          mandatory true;
          description
            "The authentication credentials used when connecting
             to this cluster node.";
        }
        leaf trace {
          tailf:info
            "Trace the communication with this node";
          type trace-flag;
          default "false";
        }
        leaf trace-output {
          tailf:info
            "Trace data output mode.";
          type trace-output;
          default "file";
          description
            "Controls how trace data is stored.";
        }
        leaf username {
          tailf:info
            "Local user name used to authenticate towards remote node";
          type string;
          tailf:non-strict-leafref {
            path "/ncs-internal:devices/ncs-internal:device/ncs-internal:config/cluster/authgroup[name=current()/../authgroup]/umap/local-user" {
              tailf:xpath-root 3;
            }
          }
          must 'not(deref(.)/../same-pass)' {
            tailf:xpath-root 3;
            error-message
              "The corresponding umap {deref(.)} for this user must not have
               same-pass configured";
            tailf:dependency "../../authgroup";
            tailf:dependency "/ncs-internal:devices/ncs-internal:device/ncs-internal:config/cluster/authgroup";
          }
          must 'deref(.) or
not(/cluster/authgroup[name=current()/../../authgroup]/
     default-map/same-pass)' {
            tailf:xpath-root 3;
            error-message
              "This user maps to the default-map, which must not have
               same-pass configured.";
            tailf:dependency "../../authgroup";
            tailf:dependency "/ncs-internal:devices/ncs-internal:device/ncs-internal:config/cluster/authgroup";
          }
          description
            "Local user name used by notification subscriber to
             authenticate towards remote node. The local user name
             will be used to look up the remote user name in the
             authgroup defined for this node. The resulting umap must
             not have same-pass configured.";
        }
        must "(/cluster/commit-queue/enabled = 'false') or username" {
          tailf:xpath-root 3;
          error-message "When commit-queue is enabled a username must be configured.";
          tailf:dependency "/ncs-internal:devices/ncs-internal:device/ncs-internal:config/cluster/commit-queue/enabled";
          tailf:dependency "username";
        }
        must "(/cluster/device-notifications/enabled = 'false') or username" {
          tailf:xpath-root 3;
          error-message "When device-notifications is enabled a username must be configured.";
          tailf:dependency "/ncs-internal:devices/ncs-internal:device/ncs-internal:config/cluster/device-notifications/enabled";
          tailf:dependency "username";
        }
        container notifications {
          description
            "NETCONF notification streams used by NCS nodes
             in a clustered environment.

             A top NCS node will automatically subscribe to these
             streams for all remote NCS nodes.

             The 'ncs-events' stream is used by the commit queue.  The
             'device-notifications' stream is used to forward NETCONF
             notifications originating from devices managed by remote
             NCS nodes.";
          // NCS drop config false list stream
        }
      }
      list authgroup {
        tailf:info
          "Authentication settings for a group of nodes";
        key "name";
        description
          "When NCS connects to a remote cluster node, it locates the
           authgroup configured for that node.  Then NCS looks up
           the local NCS user name in the 'umap' list.  If an entry is
           found, the credentials configured is used when
           authenticating to the NCS node.

           If no entry is found in the 'umap' list, the credentials
           configured in 'default-map' are used.

           If no 'default-map' has been configured, and the local NCS
           user name is not found in the 'umap' list, the connection
           to the node fails.";

        grouping remote-user-remote-auth {
          description
            "Remote authentication credentials.";
          choice remote-user {
            mandatory true;
            leaf same-user {
              tailf:info
                "Use the local NCS user name as the remote user name";
              type empty;
              description
                "Use the local NCS user name as the remote user name.";
            }
            leaf remote-name {
              tailf:info
                "Specify node user name";
              type string;
              description
                "Remote user name.";
            }
          }
          choice remote-auth {
            mandatory true;
            leaf same-pass {
              tailf:info
                "Use the local NCS password as the remote password";
              type empty;
              description
                "Use the local NCS password as the remote password.";
            }
            leaf remote-password {
              tailf:ned-ignore-compare-config;
              tailf:info
                "Specify the remote password";
              tailf:suppress-echo true;
              type tailf:aes-256-cfb-128-encrypted-string;
              description
                "Remote password.";
            }
            case public-key {
              uses public-key-auth;
            }
          }
        }
        leaf name {
          tailf:info
            "The name of the authgroup";
          type string;
          description
            "The name of the authgroup.";
        }
        container default-map {
          presence "Map unknown users";
          description
            "If an authgroup has a default-map, it is used if a local
               NCS user is not found in the umap list.";
          tailf:info
            "Remote authentication parameters for users not in umap";
          uses remote-user-remote-auth;
        }
        list umap {
          key "local-user";
          description
            "The umap is a list with the local NCS user name as key.
               It maps the local NCS user name to remote authentication
               credentials.";
          tailf:info
            "Map NCS users to remote authentication parameters";
          leaf local-user {
            type string;
            description
              "The local NCS user name.";
          }
          uses remote-user-remote-auth;
        }
      }
      container commit-queue {
        leaf enabled {
          type boolean;
          must " . = 'false' or
not (/cluster/remote-node
       [not (username)]
       [deref(authgroup)/../default-map[same-user or same-pass]])" {
            tailf:xpath-root 3;
            error-message
              "At least one remote-node has neither username nor
               a default-map not configured with either same-user or same-pass.";
            tailf:dependency "../../authgroup";
            tailf:dependency "/ncs-internal:devices/ncs-internal:device/ncs-internal:config/cluster/remote-node/authgroup";
            tailf:dependency "/ncs-internal:devices/ncs-internal:device/ncs-internal:config/cluster/remote-node/username";
          }
          must " . = 'false' or ../../remote-node" {
            tailf:xpath-root 3;
            error-message
              "At least one cluster remote-node has to be configured. All LSA
               devices must be configured as cluster devices.";
            tailf:dependency "../../remote-node";
          }
          default "false";
          description
            "Enable commit queues in cluster mode.";
        }
      }
      container device-notifications {
        leaf enabled {
          type boolean;
          must " . = 'false' or
not (/cluster/remote-node
       [not (username)]
       [deref(authgroup)/../default-map[same-user or same-pass]])" {
            tailf:xpath-root 3;
            error-message
              "At least one remote-node has neither username nor
               a default-map not configured with either same-user or same-pass.";
            tailf:dependency "../../authgroup";
            tailf:dependency "/ncs-internal:devices/ncs-internal:device/ncs-internal:config/cluster/remote-node/authgroup";
            tailf:dependency "/ncs-internal:devices/ncs-internal:device/ncs-internal:config/cluster/remote-node/username";
          }
          must " . = 'false' or ../../remote-node" {
            tailf:xpath-root 3;
            error-message
              "At least one cluster remote-node has to be configured. All LSA
               devices must be configured as cluster devices.";
            tailf:dependency "../../remote-node";
          }
          default "false";
          description
            "Enable device notifications in cluster mode.";
        }
      }
      // NCS drop config false list connection
    }
  }
  augment "/ncs-internal:devices/ncs-internal:device/ncs-internal:live-status" {
    container cluster {
      tailf:ncs-device-type "netconf";
      tailf:display-when "not(../../ncs-internal:module) or ../../ncs-internal:module[ncs-internal:name='tailf-ncs'] or (../../ncs-internal:live-status-protocol[not(ncs-internal:capability)]) or (../../ncs-internal:live-status-protocol/ncs-internal:capability/ncs-internal:module[.='tailf-ncs'])";
      tailf:info
        "Cluster configuration";
      container global-settings {
        tailf:info
          "Global settings for all remote nodes";
        container timeouts {
          description
            "Timeouts used when communicating with a remote node in the cluster.";
          leaf connect-timeout {
            tailf:info
              "Timeout in seconds for new connections";
            type uint32 {
              range "1..4294967";
            }
            // NCS drop default statement
            units "seconds";
            description
              "The timeout in seconds for new connections to a remote node.";
          }
        }
        container ssh-keep-alive {
          description
            "Controls SSH keep alive settings when communicating from this
             node to remote devices.";
          tailf:info
            "Controls SSH keep alive settings";
          leaf interval {
            type uint32 {
              range "0..4294967";
            }
            // NCS drop default statement
            units "seconds";
            description
              "Seconds between SSH keep alive activity.";
          }
          leaf count {
            type uint8;
            // NCS drop default statement
            description
              "Number of intervals to fail before failing the connection.";
          }
        }
      }
      list remote-node {
        tailf:info
          "List of configured remote nodes";
        key "name";
        leaf name {
          tailf:info
            "Name of remote node";
          // NCS drop tailf:cli-allow-range
          type live_ncs_node-name;
        }
        leaf address {
          tailf:info
            "Address of remote node (defaults to name)";
          type inet:host;
          description
            "Address of remote node. Unless set the node-name will be
             interpreted as the hostname";
        }
        leaf port {
          tailf:info
            "Port number of remote node";
          type inet:port-number;
          // NCS drop default statement
          description
            "NETCONF port of remote node.";
        }
        uses live_ncs_ssh-connection-config;
        container ssh-algorithms {
          description
            "Supported (allowed) algorithms that should be used during
             SSH algorithm negotiations.";
          // NCS expand uses statement
          leaf-list public-key {
            description
              "Supported public key algorithms. Only the ones supported by the
               underlying SSH implementation will be used.";
            type live_ncs_ssh-public-key-algorithm;
            ordered-by user;
            // NCS drop default statement
            // NCS drop default statement
            // NCS drop default statement
            // NCS drop default statement
            // NCS drop default statement
            // NCS drop default statement
          }
          leaf-list kex {
            description
              "Supported key exchange algorithms. Only the ones supported
               by the underlying SSH implementation will be used.";
            ordered-by user;
            type live_ncs_ssh-kex-algorithm;
            // NCS drop default statement
            // NCS drop default statement
            // NCS drop default statement
            // NCS drop default statement
            // NCS drop default statement
            // NCS drop default statement
            // NCS drop default statement
            // NCS drop default statement
            // NCS drop default statement
            // NCS drop default statement
          }
          leaf-list mac {
            description
              "Supported MAC algorithms. Only the ones supported by the
               underlying SSH implementation will be used.";
            ordered-by user;
            type live_ncs_ssh-mac-algorithm;
            // NCS drop default statement
            // NCS drop default statement
            // NCS drop default statement
            // NCS drop default statement
            // NCS drop default statement
            // NCS drop default statement
            // NCS drop default statement
          }
          leaf-list cipher {
            description
              "Supported cipher algorithms. Only the ones supported by the
               underlying SSH implementation will be used.";
            ordered-by user;
            type live_ncs_ssh-cipher-algorithm;
            // NCS drop default statement
            // NCS drop default statement
            // NCS drop default statement
            // NCS drop default statement
            // NCS drop default statement
            // NCS drop default statement
            // NCS drop default statement
            // NCS drop default statement
          }
          leaf-list compression {
            description
              "Supported compression algorithms. Only the ones supported by the
               underlying SSH implementation will be used.";
            ordered-by user;
            type live_ncs_ssh-compression-algorithm;
            // NCS drop default statement
            // NCS drop default statement
            // NCS drop default statement
          }
          container dh-group {
            description
              "Range of allowed group size the client will request during
                        a \"diffie-hellman-group-exchange\". The range will be the
                        intersection of these values and what the server supports";
            leaf min-size {
              // NCS drop must statement
              type live_ncs_dh-group-size-type;
              description
                "Minimal size of p in bits.";
              // NCS drop default statement
            }
            leaf preferred-size {
              // NCS drop must statement
              type live_ncs_dh-group-size-type;
              description
                "Preferred size of p in bits.";
              // NCS drop default statement
            }
            leaf max-size {
              type live_ncs_dh-group-size-type;
              description
                "Maximal size of p in bits.";
              // NCS drop default statement
            }
          }
        }
        leaf authgroup {
          tailf:info
            "Authentication credentials for the node";
          type leafref {
            path "/ncs-internal:devices/ncs-internal:device/ncs-internal:live-status/cluster/authgroup/name" {
              tailf:xpath-root 3;
            }
          }
          // NCS drop mandatory statement
          description
            "The authentication credentials used when connecting
             to this cluster node.";
        }
        leaf trace {
          tailf:info
            "Trace the communication with this node";
          type live_ncs_trace-flag;
          // NCS drop default statement
        }
        leaf trace-output {
          tailf:info
            "Trace data output mode.";
          type live_ncs_trace-output;
          // NCS drop default statement
          description
            "Controls how trace data is stored.";
        }
        leaf username {
          tailf:info
            "Local user name used to authenticate towards remote node";
          type string;
          tailf:non-strict-leafref {
            path "/ncs-internal:devices/ncs-internal:device/ncs-internal:live-status/cluster/authgroup[name=current()/../authgroup]/umap/local-user" {
              tailf:xpath-root 3;
            }
          }
          // NCS drop must statement
          // NCS drop must statement
          description
            "Local user name used by notification subscriber to
             authenticate towards remote node. The local user name
             will be used to look up the remote user name in the
             authgroup defined for this node. The resulting umap must
             not have same-pass configured.";
        }
        // NCS drop must statement
        // NCS drop must statement
        container notifications {
          description
            "NETCONF notification streams used by NCS nodes
             in a clustered environment.

             A top NCS node will automatically subscribe to these
             streams for all remote NCS nodes.

             The 'ncs-events' stream is used by the commit queue.  The
             'device-notifications' stream is used to forward NETCONF
             notifications originating from devices managed by remote
             NCS nodes.";
          list stream {
            key "name";
            // NCS drop tailf:cdb-oper
            leaf name {
              type string;
            }
            leaf status {
              type enumeration {
                enum "connecting" {
                  tailf:code-name "cluster_remotenode_notifications_connecting";
                  description
                    "The notification subscription is not yet established and
                     is periodically retried.";
                }
                enum "up" {
                  tailf:code-name "cluster_remotenode_notifications_up";
                  description
                    "The subscription is established.";
                }
              }
              // NCS drop tailf:callpoint
            }
            leaf last-event {
              type yang:date-and-time;
              description
                "Time of last received event.";
            }
            leaf received-notifications {
              type yang:zero-based-counter64;
              // NCS drop tailf:callpoint
              description
                "Number of received notifications since last reboot.";
            }
            // NCS drop fully hidden leaf 'sequence-no'
          }
        }
      }
      list authgroup {
        tailf:info
          "Authentication settings for a group of nodes";
        key "name";
        description
          "When NCS connects to a remote cluster node, it locates the
           authgroup configured for that node.  Then NCS looks up
           the local NCS user name in the 'umap' list.  If an entry is
           found, the credentials configured is used when
           authenticating to the NCS node.

           If no entry is found in the 'umap' list, the credentials
           configured in 'default-map' are used.

           If no 'default-map' has been configured, and the local NCS
           user name is not found in the 'umap' list, the connection
           to the node fails.";

        grouping remote-user-remote-auth {
          description
            "Remote authentication credentials.";
          choice remote-user {
            // NCS drop mandatory statement
            leaf same-user {
              tailf:info
                "Use the local NCS user name as the remote user name";
              type empty;
              description
                "Use the local NCS user name as the remote user name.";
            }
            leaf remote-name {
              tailf:info
                "Specify node user name";
              type string;
              description
                "Remote user name.";
            }
          }
          choice remote-auth {
            // NCS drop mandatory statement
            leaf same-pass {
              tailf:info
                "Use the local NCS password as the remote password";
              type empty;
              description
                "Use the local NCS password as the remote password.";
            }
            leaf remote-password {
              tailf:info
                "Specify the remote password";
              tailf:suppress-echo true;
              type tailf:aes-256-cfb-128-encrypted-string;
              description
                "Remote password.";
            }
            case public-key {
              uses live_ncs_public-key-auth;
            }
          }
        }
        leaf name {
          tailf:info
            "The name of the authgroup";
          type string;
          description
            "The name of the authgroup.";
        }
        container default-map {
          presence "Map unknown users";
          description
            "If an authgroup has a default-map, it is used if a local
               NCS user is not found in the umap list.";
          tailf:info
            "Remote authentication parameters for users not in umap";
          uses remote-user-remote-auth;
        }
        list umap {
          key "local-user";
          description
            "The umap is a list with the local NCS user name as key.
               It maps the local NCS user name to remote authentication
               credentials.";
          tailf:info
            "Map NCS users to remote authentication parameters";
          leaf local-user {
            type string;
            description
              "The local NCS user name.";
          }
          uses remote-user-remote-auth;
        }
      }
      container commit-queue {
        leaf enabled {
          type boolean;
          // NCS drop must statement
          // NCS drop must statement
          // NCS drop default statement
          description
            "Enable commit queues in cluster mode.";
        }
      }
      container device-notifications {
        leaf enabled {
          type boolean;
          // NCS drop must statement
          // NCS drop must statement
          // NCS drop default statement
          description
            "Enable device notifications in cluster mode.";
        }
      }
      list connection {
        // NCS drop tailf:callpoint
        description
          "The connections set up by this node to other cluster nodes";
        leaf remote-node {
          type leafref {
            path "/ncs-internal:devices/ncs-internal:device/ncs-internal:live-status/cluster/remote-node/name" {
              tailf:xpath-root 3;
            }
          }
          description
            "Name of the remote-node";
        }
        leaf address {
          type inet:ip-address;
          description
            "The IP address used to connect to the remote-node";
        }
        leaf port {
          type inet:port-number;
          description
            "The port used to connect to the remote-node";
        }
        leaf channels {
          type uint32;
          description
            "Number of open SSH channels used";
        }
        leaf local-user {
          type string;
          description
            "The name of the local user";
        }
        leaf remote-user {
          type string;
          description
            "The name used to authenticate towards the remote-node";
        }
        leaf status {
          type enumeration {
            enum "up" {
              tailf:code-name "cluster_connection_status_up";
            }
            enum "down";
          }
          description
            "Whether this connection is actually established";
        }
        leaf trace {
          type enumeration {
            enum "enabled" {
              tailf:code-name "cluster_connection_trace_enabled";
            }
            enum "disabled";
          }
          description
            "Whether this connection is currently being traced";
        }
      }
    }
  }
  augment "/ncs-internal:devices/ncs-internal:template/ncs-internal:ned-id/ncs-internal:config" {
    container cluster {
      container global-settings {
        container timeouts {
          description
            "Timeouts used when communicating with a remote node in the cluster.";
          leaf connect-timeout {
            type string;
            // NCS drop default statement
            units "seconds";
            description
              "The timeout in seconds for new connections to a remote node.";
          }
        }
        container ssh-keep-alive {
          description
            "Controls SSH keep alive settings when communicating from this
             node to remote devices.";
          leaf interval {
            type string;
            // NCS drop default statement
            units "seconds";
            description
              "Seconds between SSH keep alive activity.";
          }
          leaf count {
            type string;
            // NCS drop default statement
            description
              "Number of intervals to fail before failing the connection.";
          }
        }
      }
      list remote-node {
        // NCS patched for predictable order
        ordered-by user;
        key "name";
        leaf name {
          type ncs_template_node-name;
        }
        leaf address {
          type string;
          description
            "Address of remote node. Unless set the node-name will be
             interpreted as the hostname";
        }
        leaf port {
          type string;
          // NCS drop default statement
          description
            "NETCONF port of remote node.";
        }
        uses ncs_template_ssh-connection-config;
        container ssh-algorithms {
          description
            "Supported (allowed) algorithms that should be used during
             SSH algorithm negotiations.";
          // NCS expand uses statement
          leaf-list public-key {
            // NCS patched for predictable order
            ordered-by user;
            description
              "Supported public key algorithms. Only the ones supported by the
               underlying SSH implementation will be used.";
            type ncs_template_ssh-public-key-algorithm;
            // NCS drop default statement
            // NCS drop default statement
            // NCS drop default statement
            // NCS drop default statement
            // NCS drop default statement
            // NCS drop default statement
          }
          leaf-list kex {
            // NCS patched for predictable order
            ordered-by user;
            description
              "Supported key exchange algorithms. Only the ones supported
               by the underlying SSH implementation will be used.";
            type ncs_template_ssh-kex-algorithm;
            // NCS drop default statement
            // NCS drop default statement
            // NCS drop default statement
            // NCS drop default statement
            // NCS drop default statement
            // NCS drop default statement
            // NCS drop default statement
            // NCS drop default statement
            // NCS drop default statement
            // NCS drop default statement
          }
          leaf-list mac {
            // NCS patched for predictable order
            ordered-by user;
            description
              "Supported MAC algorithms. Only the ones supported by the
               underlying SSH implementation will be used.";
            type ncs_template_ssh-mac-algorithm;
            // NCS drop default statement
            // NCS drop default statement
            // NCS drop default statement
            // NCS drop default statement
            // NCS drop default statement
            // NCS drop default statement
            // NCS drop default statement
          }
          leaf-list cipher {
            // NCS patched for predictable order
            ordered-by user;
            description
              "Supported cipher algorithms. Only the ones supported by the
               underlying SSH implementation will be used.";
            type ncs_template_ssh-cipher-algorithm;
            // NCS drop default statement
            // NCS drop default statement
            // NCS drop default statement
            // NCS drop default statement
            // NCS drop default statement
            // NCS drop default statement
            // NCS drop default statement
            // NCS drop default statement
          }
          leaf-list compression {
            // NCS patched for predictable order
            ordered-by user;
            description
              "Supported compression algorithms. Only the ones supported by the
               underlying SSH implementation will be used.";
            type ncs_template_ssh-compression-algorithm;
            // NCS drop default statement
            // NCS drop default statement
            // NCS drop default statement
          }
          container dh-group {
            description
              "Range of allowed group size the client will request during
                        a \"diffie-hellman-group-exchange\". The range will be the
                        intersection of these values and what the server supports";
            leaf min-size {
              // NCS drop must statement
              type ncs_template_dh-group-size-type;
              description
                "Minimal size of p in bits.";
              // NCS drop default statement
            }
            leaf preferred-size {
              // NCS drop must statement
              type ncs_template_dh-group-size-type;
              description
                "Preferred size of p in bits.";
              // NCS drop default statement
            }
            leaf max-size {
              type ncs_template_dh-group-size-type;
              description
                "Maximal size of p in bits.";
              // NCS drop default statement
            }
          }
        }
        leaf authgroup {
          type string;
          // NCS drop mandatory statement
          description
            "The authentication credentials used when connecting
             to this cluster node.";
        }
        leaf trace {
          type ncs_template_trace-flag;
          // NCS drop default statement
        }
        leaf trace-output {
          type ncs_template_trace-output;
          // NCS drop default statement
          description
            "Controls how trace data is stored.";
        }
        leaf username {
          type string;
          // NCS drop must statement
          // NCS drop must statement
          description
            "Local user name used by notification subscriber to
             authenticate towards remote node. The local user name
             will be used to look up the remote user name in the
             authgroup defined for this node. The resulting umap must
             not have same-pass configured.";
        }
        // NCS drop must statement
        // NCS drop must statement
        container notifications {
          description
            "NETCONF notification streams used by NCS nodes
             in a clustered environment.

             A top NCS node will automatically subscribe to these
             streams for all remote NCS nodes.

             The 'ncs-events' stream is used by the commit queue.  The
             'device-notifications' stream is used to forward NETCONF
             notifications originating from devices managed by remote
             NCS nodes.";
          // NCS drop config false list stream
        }
      }
      list authgroup {
        // NCS patched for predictable order
        ordered-by user;
        key "name";
        description
          "When NCS connects to a remote cluster node, it locates the
           authgroup configured for that node.  Then NCS looks up
           the local NCS user name in the 'umap' list.  If an entry is
           found, the credentials configured is used when
           authenticating to the NCS node.

           If no entry is found in the 'umap' list, the credentials
           configured in 'default-map' are used.

           If no 'default-map' has been configured, and the local NCS
           user name is not found in the 'umap' list, the connection
           to the node fails.";

        grouping remote-user-remote-auth {
          description
            "Remote authentication credentials.";
          choice remote-user {
            // NCS drop mandatory statement
            leaf same-user {
              type empty;
              description
                "Use the local NCS user name as the remote user name.";
            }
            leaf remote-name {
              type string;
              description
                "Remote user name.";
            }
          }
          choice remote-auth {
            // NCS drop mandatory statement
            leaf same-pass {
              type empty;
              description
                "Use the local NCS password as the remote password.";
            }
            leaf remote-password {
              type string;
              description
                "Remote password.";
            }
            case public-key {
              uses ncs_template_public-key-auth;
            }
          }
        }
        leaf name {
          type string;
          description
            "The name of the authgroup.";
        }
        container default-map {
          presence "Map unknown users";
          description
            "If an authgroup has a default-map, it is used if a local
               NCS user is not found in the umap list.";
          uses remote-user-remote-auth;
        }
        list umap {
          // NCS patched for predictable order
          ordered-by user;
          key "local-user";
          description
            "The umap is a list with the local NCS user name as key.
               It maps the local NCS user name to remote authentication
               credentials.";
          leaf local-user {
            type string;
            description
              "The local NCS user name.";
          }
          uses remote-user-remote-auth;
        }
      }
      container commit-queue {
        leaf enabled {
          type string;
          // NCS drop must statement
          // NCS drop must statement
          // NCS drop default statement
          description
            "Enable commit queues in cluster mode.";
        }
      }
      container device-notifications {
        leaf enabled {
          type string;
          // NCS drop must statement
          // NCS drop must statement
          // NCS drop default statement
          description
            "Enable device notifications in cluster mode.";
        }
      }
      // NCS drop config false list connection
    }
  }
  augment "/ncs-internal:compliance/ncs-internal:template/ncs-internal:ned-id/ncs-internal:config" {
    container cluster {
      container global-settings {
        container timeouts {
          description
            "Timeouts used when communicating with a remote node in the cluster.";
          leaf connect-timeout {
            type string;
            // NCS drop default statement
            units "seconds";
            description
              "The timeout in seconds for new connections to a remote node.";
          }
        }
        container ssh-keep-alive {
          description
            "Controls SSH keep alive settings when communicating from this
             node to remote devices.";
          leaf interval {
            type string;
            // NCS drop default statement
            units "seconds";
            description
              "Seconds between SSH keep alive activity.";
          }
          leaf count {
            type string;
            // NCS drop default statement
            description
              "Number of intervals to fail before failing the connection.";
          }
        }
      }
      list remote-node {
        // NCS patched for predictable order
        ordered-by user;
        key "name";
        leaf name {
          type ncs_compliance_template_node-name;
        }
        leaf address {
          type string;
          description
            "Address of remote node. Unless set the node-name will be
             interpreted as the hostname";
        }
        leaf port {
          type string;
          // NCS drop default statement
          description
            "NETCONF port of remote node.";
        }
        uses ncs_compliance_template_ssh-connection-config;
        container ssh-algorithms {
          description
            "Supported (allowed) algorithms that should be used during
             SSH algorithm negotiations.";
          // NCS expand uses statement
          leaf-list public-key {
            // NCS patched for predictable order
            ordered-by user;
            description
              "Supported public key algorithms. Only the ones supported by the
               underlying SSH implementation will be used.";
            type ncs_compliance_template_ssh-public-key-algorithm;
            // NCS drop default statement
            // NCS drop default statement
            // NCS drop default statement
            // NCS drop default statement
            // NCS drop default statement
            // NCS drop default statement
          }
          leaf-list kex {
            // NCS patched for predictable order
            ordered-by user;
            description
              "Supported key exchange algorithms. Only the ones supported
               by the underlying SSH implementation will be used.";
            type ncs_compliance_template_ssh-kex-algorithm;
            // NCS drop default statement
            // NCS drop default statement
            // NCS drop default statement
            // NCS drop default statement
            // NCS drop default statement
            // NCS drop default statement
            // NCS drop default statement
            // NCS drop default statement
            // NCS drop default statement
            // NCS drop default statement
          }
          leaf-list mac {
            // NCS patched for predictable order
            ordered-by user;
            description
              "Supported MAC algorithms. Only the ones supported by the
               underlying SSH implementation will be used.";
            type ncs_compliance_template_ssh-mac-algorithm;
            // NCS drop default statement
            // NCS drop default statement
            // NCS drop default statement
            // NCS drop default statement
            // NCS drop default statement
            // NCS drop default statement
            // NCS drop default statement
          }
          leaf-list cipher {
            // NCS patched for predictable order
            ordered-by user;
            description
              "Supported cipher algorithms. Only the ones supported by the
               underlying SSH implementation will be used.";
            type ncs_compliance_template_ssh-cipher-algorithm;
            // NCS drop default statement
            // NCS drop default statement
            // NCS drop default statement
            // NCS drop default statement
            // NCS drop default statement
            // NCS drop default statement
            // NCS drop default statement
            // NCS drop default statement
          }
          leaf-list compression {
            // NCS patched for predictable order
            ordered-by user;
            description
              "Supported compression algorithms. Only the ones supported by the
               underlying SSH implementation will be used.";
            type ncs_compliance_template_ssh-compression-algorithm;
            // NCS drop default statement
            // NCS drop default statement
            // NCS drop default statement
          }
          container dh-group {
            description
              "Range of allowed group size the client will request during
                        a \"diffie-hellman-group-exchange\". The range will be the
                        intersection of these values and what the server supports";
            leaf min-size {
              // NCS drop must statement
              type ncs_compliance_template_dh-group-size-type;
              description
                "Minimal size of p in bits.";
              // NCS drop default statement
            }
            leaf preferred-size {
              // NCS drop must statement
              type ncs_compliance_template_dh-group-size-type;
              description
                "Preferred size of p in bits.";
              // NCS drop default statement
            }
            leaf max-size {
              type ncs_compliance_template_dh-group-size-type;
              description
                "Maximal size of p in bits.";
              // NCS drop default statement
            }
          }
        }
        leaf authgroup {
          type string;
          // NCS drop mandatory statement
          description
            "The authentication credentials used when connecting
             to this cluster node.";
        }
        leaf trace {
          type ncs_compliance_template_trace-flag;
          // NCS drop default statement
        }
        leaf trace-output {
          type ncs_compliance_template_trace-output;
          // NCS drop default statement
          description
            "Controls how trace data is stored.";
        }
        leaf username {
          type string;
          // NCS drop must statement
          // NCS drop must statement
          description
            "Local user name used by notification subscriber to
             authenticate towards remote node. The local user name
             will be used to look up the remote user name in the
             authgroup defined for this node. The resulting umap must
             not have same-pass configured.";
        }
        // NCS drop must statement
        // NCS drop must statement
        container notifications {
          description
            "NETCONF notification streams used by NCS nodes
             in a clustered environment.

             A top NCS node will automatically subscribe to these
             streams for all remote NCS nodes.

             The 'ncs-events' stream is used by the commit queue.  The
             'device-notifications' stream is used to forward NETCONF
             notifications originating from devices managed by remote
             NCS nodes.";
          // NCS drop config false list stream
        }
      }
      list authgroup {
        // NCS patched for predictable order
        ordered-by user;
        key "name";
        description
          "When NCS connects to a remote cluster node, it locates the
           authgroup configured for that node.  Then NCS looks up
           the local NCS user name in the 'umap' list.  If an entry is
           found, the credentials configured is used when
           authenticating to the NCS node.

           If no entry is found in the 'umap' list, the credentials
           configured in 'default-map' are used.

           If no 'default-map' has been configured, and the local NCS
           user name is not found in the 'umap' list, the connection
           to the node fails.";

        grouping remote-user-remote-auth {
          description
            "Remote authentication credentials.";
          choice remote-user {
            // NCS drop mandatory statement
            leaf same-user {
              type empty;
              description
                "Use the local NCS user name as the remote user name.";
            }
            leaf remote-name {
              type string;
              description
                "Remote user name.";
            }
          }
          choice remote-auth {
            // NCS drop mandatory statement
            leaf same-pass {
              type empty;
              description
                "Use the local NCS password as the remote password.";
            }
            leaf remote-password {
              type string;
              description
                "Remote password.";
            }
            case public-key {
              uses ncs_compliance_template_public-key-auth;
            }
          }
        }
        leaf name {
          type string;
          description
            "The name of the authgroup.";
        }
        container default-map {
          presence "Map unknown users";
          description
            "If an authgroup has a default-map, it is used if a local
               NCS user is not found in the umap list.";
          uses remote-user-remote-auth;
        }
        list umap {
          // NCS patched for predictable order
          ordered-by user;
          key "local-user";
          description
            "The umap is a list with the local NCS user name as key.
               It maps the local NCS user name to remote authentication
               credentials.";
          leaf local-user {
            type string;
            description
              "The local NCS user name.";
          }
          uses remote-user-remote-auth;
        }
      }
      container commit-queue {
        leaf enabled {
          type string;
          // NCS drop must statement
          // NCS drop must statement
          // NCS drop default statement
          description
            "Enable commit queues in cluster mode.";
        }
      }
      container device-notifications {
        leaf enabled {
          type string;
          // NCS drop must statement
          // NCS drop must statement
          // NCS drop default statement
          description
            "Enable device notifications in cluster mode.";
        }
      }
      // NCS drop config false list connection
    }
  }
}
