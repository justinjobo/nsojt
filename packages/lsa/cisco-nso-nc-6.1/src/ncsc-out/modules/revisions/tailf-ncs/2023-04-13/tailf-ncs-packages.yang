submodule tailf-ncs-packages {
  // Generated by yanger -t ncs
  tailf:mount-id "cisco-nso-nc-6.1:cisco-nso-nc-6.1";

  yang-version 1.1;
  belongs-to tailf-ncs {
    prefix ncs;
  }

  import tailf-ncs-ned {
    prefix ned;
  }
  import tailf-common {
    prefix tailf;
  }
  import tailf-ncs-internal-mount {
    prefix ncs-internal;
  }

  organization
    "Tail-f Systems";
  description
    "This submodule defines the Tail-f NCS package model.

     Copyright 2012-2022 Cisco Systems, Inc.
     All rights reserved.
     Permission is hereby granted to redistribute this file without
     modification.";

  revision 2023-04-04 {
    description
      "Released as part of NCS-6.1.

       Updated description of /packages/ha/sync regarding none role.";
  }
  revision 2022-09-29 {
    description
      "Released as part of NCS-6.0.

       Updated description of /packages/ha/sync regarding deleted package.

       Added leaf-list /packages/package/oper-status/warnings.

       Added 'wait-commit-queue-empty' to reload params.

       Updated the /packages/ha container when expression.

       Added /packages/package/ncs-max-version and
       /packages/package/required-package/max-version.

       Editorial changes replacing NSO with NCS.";
  }
  revision 2022-04-12 {
    description
      "Released as part of NCS-5.8.

       Added leaf-list 'supported-ned-id-match'
       in grouping 'package-meta-data'.

       Added presence container 'and-reload' as an input param to
       /packages/ha/sync action.";
  }
  revision 2021-12-17 {
    description
      "Released as part of NCS-5.7.

       Non-backward-compatible changes have been introduced.

       Added leaf 'callpoint-model' under the 'python-package' container
       in grouping 'package-meta-data'.

       Added when expression on 'vm-name' under the 'python-package' container
       requiring 'callpoint-model' to be 'threading'.

       Added /packages/ha/sync action to transfer
       packages from primary to secondary nodes.";
  }
  revision 2021-09-02 {
    description
      "Released as part of NCS-5.6.

       Non-backwards-compatible changes have been introduced.

       Changed /packages/oper-status/error-info from leaf to leaf-list.";
  }
  revision 2020-06-25 {
    description
      "Released as part of NCS-5.4.

       Added leaf-list 'supported-ned-id' and leaf 'template-loading-mode'
       in grouping 'package-meta-data'.

       Added typedef 'package-version' at the top level matching the typedef
       'version' declared in grouping 'package-meta-data'.";
  }
  revision 2019-11-28 {
    description
      "Released as part of NCS-5.3.

       Added leaf 'python-uninitialized' under choice 'status' in
       /packages/package/oper-status container.

       Added support for Python upgrade components.

       Moved /packages/package/component/upgrade/java-class-name to a case
        'java' in choice /packages/package/component/upgrade/type.

       Added leaf 'python-class-name' to a case 'python' in choice
       /packages/package/component/upgrade/type.";
  }
  revision 2019-04-09 {
    description
      "Released as part of NCS-5.1.

       Changed ned-type 'snmp' from an empty leaf to a container.";
  }
  revision 2017-09-28 {
    description
      "Released as part of NCS-4.5.

       Added input parameter 'force' to /packages/reload action.";
  }
  revision 2017-03-16 {
    description
      "Released as part of NCS-4.4.

       Added range to all config leafs specifying time.";
  }
  revision 2016-11-24 {
    description
      "Released as part of NCS-4.3.

       Changed ned-type 'netconf' from an empty leaf to a container.";
  }
  revision 2016-05-26 {
    description
      "Released as part of NCS-4.2.

       Added /packages/package/component/entitlement-tag.";
  }
  revision 2015-06-16 {
    description
      "Released as part of NCS-4.0.

       Added support for Python packages.

       Added support for Erlang packages.

       Added /packages/package/python-package.
       Moved /packages/package/component/java-class-name to a case
        'java' in a choice /packages/package/component/type.";
  }
  revision 2014-11-19 {
    description
      "Released as part of NCS-3.3.

       Added /packages/package/build-info.";
  }
  revision 2014-06-30 {
    description
      "Released as part of NCS-3.2.

       Changed the output of action /packages/reload from a string to
         a list of result for each package.

       Added the NED option 'allow-abbrevs'.";
  }
  revision 2014-04-02 {
    description
      "Released as part of NCS-3.1.

       Changed /packages/package/ncs-min-version.";
  }
  revision 2013-11-12 {
    description
      "Released as part of NCS-3.0.

       Added /packages/package/oper-status/circular-dependency.

       Added /packages/package/component/upgrade.

       Removed /packages/package/component/service.

       Added /packages/package/templates.";
  }
  revision 2013-06-18 {
    description
      "Released as part of NCS-2.3.

       Added /packages/package/directory.

       Added /packages/reload action.";
  }
  revision 2013-03-12 {
    description
      "Released as part of NCS-2.2.

       Added 'templates' directory to the package file structure.";
  }
  revision 2012-11-13 {
    description
      "Released as part of NCS-2.1.

       Added /packages/package/component/service/java-trigger-class-name.";
  }
  revision 2012-10-04 {
    description
      "Released as part of NCS-2.0.2

       Added /packages/oper-status/error-info.";
  }
  revision 2012-08-30 {
    description
      "Released as part of NCS-2.0.";
  }

  typedef ncs_compliance_template_package-version {
    type string;
    description
      "The format of the NCS package version.";
  }

  typedef ncs_template_package-version {
    type string;
    description
      "The format of the NCS package version.";
  }

  typedef ncs_rpc_notif_package-version {
    type string {
      pattern '\d+\.\d+([-.](\d+|\w+))*';
    }
    description
      "The format of the NCS package version.";
  }

  typedef live_ncs_package-version {
    type string {
      pattern '\d+\.\d+([-.](\d+|\w+))*';
    }
    description
      "The format of the NCS package version.";
  }

  typedef package-version {
    type string {
      pattern '\d+\.\d+([-.](\d+|\w+))*';
    }
    description
      "The format of the NCS package version.";
  }

  grouping ncs_compliance_template_package-meta-data {
    description
      "This grouping describes meta-data for a NCS package.

       A NCS package has the following file structure:

         <package-name>/package-meta-data.xml
                        load-dir/
                        cdb/
                        shared-jar/
                        private-jar/
                        erlang-lib/
                        python/
                        webui/
                        templates/
                        scripts/
                        src/
                        doc/
                        netsim/

       The package-meta-data.xml file contains a top-level element
       'ncs-package' in the namespace defined by this module, which
       behaves as if defined as:

         container ncs-package {
           uses package-meta-data;
         }

       The optional 'load-dir' directory is appended to the
       'load-path' of NCS.  It contains fxs files and ccl files
       etc. It can also contain .xml files, which will be loaded by
       CDB during init and upgrade (i.e. these files can be used to
       include inital CDB data needed by the package).

       The optional 'shared-jar' directory contains jar files with
       Java code that is shared among all packages. Once loaded, this
       code cannot be modified without reloading all jar files for all
       packages.

       The optional 'private-jar' directory contains jar files with
       Java code that are loaded by a package-spefic class loader.
       Thus, this code is not available from other packages.  By
       putting for example the code for a specific service in a
       private jar, NCS can dynamically upgrade the service without
       affecting any other service.

       The optional 'erlang-lib' directory contains Erlang
       applications.

       The optional 'python' directory contains Python code for the
       component.

       The optional 'webui' directory contains webui customization
       files.

       The optional 'templates' directory contains templates for
       template-based services.";

    typedef version {
      type ncs_compliance_template_package-version;
      description
        "The version is a sequence of numbers and words, separated by '.'
         or '-'.  When NCS compares a version string, it parses the string
         into the sequence of numbers and words, and compares each component
         individually.";
    }
    leaf name {
      type string;
      // NCS drop mandatory statement
      description
        "A unique name, used to identify the package.";
    }
    leaf package-version {
      type version;
      // NCS drop mandatory statement
      description
        "The version of the package. An NCS customer that modifies a package
         is encouraged to add its own info to this string, e.g.
           1.2-acme-1
           1.2-acme-2";
    }
    leaf description {
      type string;
      description
        "Free-form text describing the package.";
    }
    leaf-list ncs-min-version {
      // NCS patched for predictable order
      ordered-by user;
      type version;
      description
        "Minimum NCS versions, one per NCS major, required by this package.";
    }
    leaf-list ncs-max-version {
      // NCS patched for predictable order
      ordered-by user;
      type version;
      description
        "Maximum NCS versions, one per NCS major, required by this package.";
    }
    container python-package {
      presence "Python specific package data";
      leaf vm-name {
        type string;
        // NCS drop when statement
        description
          "A Python package will per default run in a seperate Python VM.
           This Python VM will get a symbolic name (for reference from
           within NCS) which per default is the package 'name'.

           However, by setting 'vm-name', its value will be used as as
           the symbolic name for the Python VM started. This will
           cause packages with the same 'vm-name' to run in the same
           Python VM.";
      }
      leaf callpoint-model {
        type string;
        // NCS drop default statement
        description
          "A Python package will per default run all Services, Nano Services
           and Actions in the same OS process. If this is set to multiprocessing
           a separate worker process will be created for each Service,
           Nano Service and Action.

           In parallel workloads the multiprocessing callpoint model
           can improve the performance of the services";
      }
    }
    leaf directory {
      type string;
      description
        "The path to the directory of the package.";
    }
    leaf-list templates {
      // NCS patched for predictable order
      ordered-by user;
      type string;
      description
        "The templates defined by this package.";
    }
    leaf template-loading-mode {
      type string;
      description
        "This leaf indicates whether the templates in this package are
         interpreted in strict mode or relaxed mode. It is unset if the package
         has no templates.

         Strict mode means we report all schema-related errors in templates
         that can be identified at load time (such as unknown namespace, schema
         ambiguity or unknown ned-id). Strict mode is applid when there are no
         supported-ned-ids declared or when all of the supported-ned-ids are
         loaded.

         If the package declares supported-ned-ids, but some of them are not
         recognized, then we assume relaxed mode as we will not be able to
         identify some of the schema-related errors, for example we might need
         to skip over tags in unknown namespaces because they might belong
         to the missing ned-ids that the package supports, but that are
         currently not loaded in the runtime system.

         It is important that the package developer tests the package with
         all the supported-ned-ids loaded, i.e. in strict mode, as it helps
         catch errors that may be ignored in relaxed mode.";
    }
    leaf-list supported-ned-id {
      // NCS patched for predictable order
      ordered-by user;
      type string;
      description
        "Templates defined by this package will be applied in the scope of
         this list of ned-ids. Trying to apply a template defined by this
         package to a device with a different ned-id will result at runtime
         error. If no supported-ned-id is defined, then no such restrictions
         are placed on this package's templates, however it may lead to a
         situation where loading an additional NED can prevent the package
         defining the template from loading by making a template ambiguous.

         This parameter has no effect for packages that define no templates.";
    }
    leaf-list supported-ned-id-match {
      // NCS patched for predictable order
      ordered-by user;
      type string;
      description
        "This list is used to populate 'supported-ned-id' with the help
         of regular expressions. Ned-ids in the system that match at least
         one of the regular expressions in this list are added to the
         'supported-ned-id' list.";
    }
    list required-package {
      // NCS patched for predictable order
      ordered-by user;
      key "name";
      description
        "A list of packages required by this package.  NCS will not
         load any package with missing dependencies.";
      leaf name {
        type string;
      }
      leaf min-version {
        type version;
        description
          "Minimum version required by this package.";
      }
      leaf max-version {
        type version;
        description
          "Maximum version required by this package.";
      }
    }
    list component {
      // NCS patched for predictable order
      ordered-by user;
      key "name";
      leaf name {
        type string;
        description
          "A unique name, used to identify the component within
           the package.";
      }
      leaf description {
        type string;
        description
          "Free-form text describing the component.";
      }
      leaf entitlement-tag {
        type string;
        description
          "Identifies the component for Smart Licensing.";
      }
      choice type {
        // NCS drop mandatory statement
        case ned {
          description
            "A NED package typically contains the YANG models for
             the device, and Java classes derived from these modules.
             The Java classes are delivered as 'shared' jar files, which
             makes them available for Java services and other Java code
             to use.";
          container ned {
            choice ned-type {
              // NCS drop mandatory statement
              container netconf {
                description
                  "A NETCONF NED typically consists of the YANG modules
                   for the device, and Java classes derived from these
                   modules.";
                leaf ned-id {
                  type string;
                  // NCS drop mandatory statement
                  description
                    "The identity that identifies the NETCONF NED. If
                     let empty it is just a plain NETCONF NED.";
                }
              }
              container snmp {
                description
                  "An SNMP NED typically consists of the MIB modules
                   for the device, YANG modules derived from the MIBs, and
                   Java classes derived from these models.";
                leaf ned-id {
                  type string;
                  description
                    "The identity that identifies the SNMP NED.";
                }
              }
              container cli {
                description
                  "A CLI NED typically consists of YANG models for the
                   device, Java classes derived from these modules, and
                   a Java class responsible for the communication with the
                   device.";
                leaf ned-id {
                  type string;
                  // NCS drop mandatory statement
                  description
                    "The identity that identifies the CLI NED.  All
                     devices of type 'cli' that are configured with
                     this 'ned-id' are handled by this compontent's 'NedCli'
                     Java class.";
                }
                leaf java-class-name {
                  type string;
                  // NCS drop mandatory statement
                  description
                    "The name of the Java class that implements the
                     interface 'NedCli'.";
                }
              }
              container generic {
                description
                  "A Generic NED typically consists of YANG models for the
                   device, Java classes derived from these modules, and
                   a Java class responsible for the communication with the
                   device.";
                leaf ned-id {
                  type string;
                  // NCS drop mandatory statement
                  description
                    "The identity that identifies the Generic NED.  All
                     devices of type 'generic' that are configured with
                     this 'ned-id' are handled by this component's 'NedGeneric'
                     Java class.";
                }
                leaf java-class-name {
                  type string;
                  // NCS drop mandatory statement
                  description
                    "The name of the Java class that implements the
                     interface 'NedGeneric'.";
                }
              }
            }
            container device {
              leaf vendor {
                type string;
                // NCS drop mandatory statement
                description
                  "Free-form string, used for documentation purposes.";
              }
              leaf product-family {
                type string;
                description
                  "The product-specific family of products supported by this
                   NED.

                   In some cases, this could be as generic as 'ios', if the
                   NED works with any ios release.  In other cases it could
                   be as specific as 'ios-11.4' if it works only with ios
                   release 11.4.  And in some cases, it would be some middle
                   ground, e.g., 'ios-11' or 'ios-11+'.";
              }
            }
            list option {
              // NCS patched for predictable order
              ordered-by user;
              key "name";
              description
                "A list of options to configure the behavior of this NED.
                 Available options are:

                  ordered-diff (for generic NEDs),
                     Order the operations sent the NED such that
                     dependencies are taken into account, ie if a
                     list element is deleted and there are leafref
                     references to the instance, order the leafref
                     in front of the delete of the instance.

                  show-tag (for CLI NEDs)
                     If set the NED will only ask for one top-tag in
                     the show() callback instead of invoking the show()
                     callback once for each top-tag. Many NEDs return
                     the entire configuration in one go and are only
                     interested in one show() invocation. The common
                     workaround is to only return when the show() command
                     is invoked with a specific top-tag, and return the
                     empty string for the rest. With this option set
                     there will only be one show() invocation.

                  allow-abbrevs (for CLI NEDs)
                     When set abbreviated commands are allowed to be
                     sent in the response to the show() callback. Devices
                     typically do not generate abbreviated commands and
                     setting the above option may introduce ambiguity in
                     the parsing.

                  show-partial
                    Set if the NED supports partial show.
                ";
              leaf name {
                type string;
              }
              leaf value {
                type string;
              }
            }
          }
        }
        case upgrade {
          description
            "An upgrade component is used to migrate data for packages
             where the YANG data model has changed and the automatic
             CDB upgrade is not sufficient. The upgrade component
             consists of either a Java class with a main method or a
             Python class with an upgrade method, that is expected to
             run one time only.";
          container upgrade {
            choice type {
              // NCS drop mandatory statement
              case java {
                leaf java-class-name {
                  type string;
                  description
                    "The name of the Java class that implements a main method
                     which will migrate data.";
                }
              }
              case python {
                leaf python-class-name {
                  type string;
                  description
                    "Name of the Python class that implements an upgrade
                     method which will migrate data.";
                }
              }
            }
          }
        }
        case callback {
          description
            "A data-provider can be used to implement NCS,
             services, external data providers, etc.";
          container callback {
            leaf-list java-class-name {
              // NCS patched for predictable order
              ordered-by user;
              type string;
              // NCS drop min-elements statement
              description
                "The name of the Java class that is annotated with one of
                 the callback annotations 'ServiceCallback', 'ActionCallback',
                 'AuthCallback', 'DataCallback', 'DBCallback',
                 'SnmpInformResponseCallback', 'TransCallback',
                 'TransValidateCallback', or 'ValidateCallback'.";
            }
          }
        }
        case application {
          description
            "An application is a generic type with some
             Java code, and a Java class that is instantiated by NCS.";
          container application {
            choice type {
              // NCS drop mandatory statement
              case java {
                description
                  "Java application";
                leaf java-class-name {
                  type string;
                  // NCS drop mandatory statement
                  description
                    "The name of the Java class that implements the
                     interface 'com.tailf.ncs.ApplicationComponent'.";
                }
              }
              case python {
                description
                  "Python application";
                leaf python-class-name {
                  type string;
                  // NCS drop mandatory statement
                  description
                    "The name of the Python class that will be started by NCS.

                     An empty string here indicates a Python Library,
                     i.e., no code will be invoked by NCS. However, other
                     packages may depend on this package, thus getting the
                     PYTHONPATH setup to point to this package.";
                }
              }
            }
            leaf start-phase {
              type string;
              // NCS drop default statement
              description
                "The start phase where the package is instantiated.";
            }
          }
        }
      }
    }
  }

  grouping ncs_compliance_template_reload-params {
    leaf max-wait-time {
      type string;
      units "seconds";
      // NCS drop default statement
      description
        "When a reload includes updated YANG code (.fxs files) or
         CLI specification files (.ccl files), NCS needs to run
         a data model upgrade procedure. This requires that all
         transactions are closed, in particular that users having
         CLI sessions in configure mode must exit to operational
         mode. The 'max-wait-time' is the maximum time to wait for
         this to complete.";
    }
    leaf timeout-action {
      type string;
      // NCS drop default statement
      description
        "If 'max-wait-time' is reached with transactions still open,
         the reload will be canceled if 'timeout-action' is 'fail'.
         If 'timeout-action' is 'kill', any remaining transactions
         will instead be forcibly terminated, and the reload will
         proceed.";
    }
    leaf force {
      description
        "If this parameter is not given, then the action may abort if
         some dangerous operations need to be performed, such as removal of
         the whole namespace. By using this parameter the operator
         acknowledges this, and allows to proceed with the dangerous
         operations.";
      type empty;
    }
    leaf wait-commit-queue-empty {
      type empty;
      description
        "If the reload includes updated YANG code (.fxs files) or CLI
         specification files (.ccl files), it will block new transactions
         and wait for all the ongoing queue items to finish. The reload
         proceeds when the commit queue becomes empty. Otherwise, it will
         stop with an error.";
    }
  }

  grouping ncs_template_package-meta-data {
    description
      "This grouping describes meta-data for a NCS package.

       A NCS package has the following file structure:

         <package-name>/package-meta-data.xml
                        load-dir/
                        cdb/
                        shared-jar/
                        private-jar/
                        erlang-lib/
                        python/
                        webui/
                        templates/
                        scripts/
                        src/
                        doc/
                        netsim/

       The package-meta-data.xml file contains a top-level element
       'ncs-package' in the namespace defined by this module, which
       behaves as if defined as:

         container ncs-package {
           uses package-meta-data;
         }

       The optional 'load-dir' directory is appended to the
       'load-path' of NCS.  It contains fxs files and ccl files
       etc. It can also contain .xml files, which will be loaded by
       CDB during init and upgrade (i.e. these files can be used to
       include inital CDB data needed by the package).

       The optional 'shared-jar' directory contains jar files with
       Java code that is shared among all packages. Once loaded, this
       code cannot be modified without reloading all jar files for all
       packages.

       The optional 'private-jar' directory contains jar files with
       Java code that are loaded by a package-spefic class loader.
       Thus, this code is not available from other packages.  By
       putting for example the code for a specific service in a
       private jar, NCS can dynamically upgrade the service without
       affecting any other service.

       The optional 'erlang-lib' directory contains Erlang
       applications.

       The optional 'python' directory contains Python code for the
       component.

       The optional 'webui' directory contains webui customization
       files.

       The optional 'templates' directory contains templates for
       template-based services.";

    typedef version {
      type ncs_template_package-version;
      description
        "The version is a sequence of numbers and words, separated by '.'
         or '-'.  When NCS compares a version string, it parses the string
         into the sequence of numbers and words, and compares each component
         individually.";
    }
    leaf name {
      type string;
      // NCS drop mandatory statement
      description
        "A unique name, used to identify the package.";
    }
    leaf package-version {
      type version;
      // NCS drop mandatory statement
      description
        "The version of the package. An NCS customer that modifies a package
         is encouraged to add its own info to this string, e.g.
           1.2-acme-1
           1.2-acme-2";
    }
    leaf description {
      type string;
      description
        "Free-form text describing the package.";
    }
    leaf-list ncs-min-version {
      // NCS patched for predictable order
      ordered-by user;
      type version;
      description
        "Minimum NCS versions, one per NCS major, required by this package.";
    }
    leaf-list ncs-max-version {
      // NCS patched for predictable order
      ordered-by user;
      type version;
      description
        "Maximum NCS versions, one per NCS major, required by this package.";
    }
    container python-package {
      presence "Python specific package data";
      leaf vm-name {
        type string;
        // NCS drop when statement
        description
          "A Python package will per default run in a seperate Python VM.
           This Python VM will get a symbolic name (for reference from
           within NCS) which per default is the package 'name'.

           However, by setting 'vm-name', its value will be used as as
           the symbolic name for the Python VM started. This will
           cause packages with the same 'vm-name' to run in the same
           Python VM.";
      }
      leaf callpoint-model {
        type string;
        // NCS drop default statement
        description
          "A Python package will per default run all Services, Nano Services
           and Actions in the same OS process. If this is set to multiprocessing
           a separate worker process will be created for each Service,
           Nano Service and Action.

           In parallel workloads the multiprocessing callpoint model
           can improve the performance of the services";
      }
    }
    leaf directory {
      type string;
      description
        "The path to the directory of the package.";
    }
    leaf-list templates {
      // NCS patched for predictable order
      ordered-by user;
      type string;
      description
        "The templates defined by this package.";
    }
    leaf template-loading-mode {
      type string;
      description
        "This leaf indicates whether the templates in this package are
         interpreted in strict mode or relaxed mode. It is unset if the package
         has no templates.

         Strict mode means we report all schema-related errors in templates
         that can be identified at load time (such as unknown namespace, schema
         ambiguity or unknown ned-id). Strict mode is applid when there are no
         supported-ned-ids declared or when all of the supported-ned-ids are
         loaded.

         If the package declares supported-ned-ids, but some of them are not
         recognized, then we assume relaxed mode as we will not be able to
         identify some of the schema-related errors, for example we might need
         to skip over tags in unknown namespaces because they might belong
         to the missing ned-ids that the package supports, but that are
         currently not loaded in the runtime system.

         It is important that the package developer tests the package with
         all the supported-ned-ids loaded, i.e. in strict mode, as it helps
         catch errors that may be ignored in relaxed mode.";
    }
    leaf-list supported-ned-id {
      // NCS patched for predictable order
      ordered-by user;
      type string;
      description
        "Templates defined by this package will be applied in the scope of
         this list of ned-ids. Trying to apply a template defined by this
         package to a device with a different ned-id will result at runtime
         error. If no supported-ned-id is defined, then no such restrictions
         are placed on this package's templates, however it may lead to a
         situation where loading an additional NED can prevent the package
         defining the template from loading by making a template ambiguous.

         This parameter has no effect for packages that define no templates.";
    }
    leaf-list supported-ned-id-match {
      // NCS patched for predictable order
      ordered-by user;
      type string;
      description
        "This list is used to populate 'supported-ned-id' with the help
         of regular expressions. Ned-ids in the system that match at least
         one of the regular expressions in this list are added to the
         'supported-ned-id' list.";
    }
    list required-package {
      // NCS patched for predictable order
      ordered-by user;
      key "name";
      description
        "A list of packages required by this package.  NCS will not
         load any package with missing dependencies.";
      leaf name {
        type string;
      }
      leaf min-version {
        type version;
        description
          "Minimum version required by this package.";
      }
      leaf max-version {
        type version;
        description
          "Maximum version required by this package.";
      }
    }
    list component {
      // NCS patched for predictable order
      ordered-by user;
      key "name";
      leaf name {
        type string;
        description
          "A unique name, used to identify the component within
           the package.";
      }
      leaf description {
        type string;
        description
          "Free-form text describing the component.";
      }
      leaf entitlement-tag {
        type string;
        description
          "Identifies the component for Smart Licensing.";
      }
      choice type {
        // NCS drop mandatory statement
        case ned {
          description
            "A NED package typically contains the YANG models for
             the device, and Java classes derived from these modules.
             The Java classes are delivered as 'shared' jar files, which
             makes them available for Java services and other Java code
             to use.";
          container ned {
            choice ned-type {
              // NCS drop mandatory statement
              container netconf {
                description
                  "A NETCONF NED typically consists of the YANG modules
                   for the device, and Java classes derived from these
                   modules.";
                leaf ned-id {
                  type string;
                  // NCS drop mandatory statement
                  description
                    "The identity that identifies the NETCONF NED. If
                     let empty it is just a plain NETCONF NED.";
                }
              }
              container snmp {
                description
                  "An SNMP NED typically consists of the MIB modules
                   for the device, YANG modules derived from the MIBs, and
                   Java classes derived from these models.";
                leaf ned-id {
                  type string;
                  description
                    "The identity that identifies the SNMP NED.";
                }
              }
              container cli {
                description
                  "A CLI NED typically consists of YANG models for the
                   device, Java classes derived from these modules, and
                   a Java class responsible for the communication with the
                   device.";
                leaf ned-id {
                  type string;
                  // NCS drop mandatory statement
                  description
                    "The identity that identifies the CLI NED.  All
                     devices of type 'cli' that are configured with
                     this 'ned-id' are handled by this compontent's 'NedCli'
                     Java class.";
                }
                leaf java-class-name {
                  type string;
                  // NCS drop mandatory statement
                  description
                    "The name of the Java class that implements the
                     interface 'NedCli'.";
                }
              }
              container generic {
                description
                  "A Generic NED typically consists of YANG models for the
                   device, Java classes derived from these modules, and
                   a Java class responsible for the communication with the
                   device.";
                leaf ned-id {
                  type string;
                  // NCS drop mandatory statement
                  description
                    "The identity that identifies the Generic NED.  All
                     devices of type 'generic' that are configured with
                     this 'ned-id' are handled by this component's 'NedGeneric'
                     Java class.";
                }
                leaf java-class-name {
                  type string;
                  // NCS drop mandatory statement
                  description
                    "The name of the Java class that implements the
                     interface 'NedGeneric'.";
                }
              }
            }
            container device {
              leaf vendor {
                type string;
                // NCS drop mandatory statement
                description
                  "Free-form string, used for documentation purposes.";
              }
              leaf product-family {
                type string;
                description
                  "The product-specific family of products supported by this
                   NED.

                   In some cases, this could be as generic as 'ios', if the
                   NED works with any ios release.  In other cases it could
                   be as specific as 'ios-11.4' if it works only with ios
                   release 11.4.  And in some cases, it would be some middle
                   ground, e.g., 'ios-11' or 'ios-11+'.";
              }
            }
            list option {
              // NCS patched for predictable order
              ordered-by user;
              key "name";
              description
                "A list of options to configure the behavior of this NED.
                 Available options are:

                  ordered-diff (for generic NEDs),
                     Order the operations sent the NED such that
                     dependencies are taken into account, ie if a
                     list element is deleted and there are leafref
                     references to the instance, order the leafref
                     in front of the delete of the instance.

                  show-tag (for CLI NEDs)
                     If set the NED will only ask for one top-tag in
                     the show() callback instead of invoking the show()
                     callback once for each top-tag. Many NEDs return
                     the entire configuration in one go and are only
                     interested in one show() invocation. The common
                     workaround is to only return when the show() command
                     is invoked with a specific top-tag, and return the
                     empty string for the rest. With this option set
                     there will only be one show() invocation.

                  allow-abbrevs (for CLI NEDs)
                     When set abbreviated commands are allowed to be
                     sent in the response to the show() callback. Devices
                     typically do not generate abbreviated commands and
                     setting the above option may introduce ambiguity in
                     the parsing.

                  show-partial
                    Set if the NED supports partial show.
                ";
              leaf name {
                type string;
              }
              leaf value {
                type string;
              }
            }
          }
        }
        case upgrade {
          description
            "An upgrade component is used to migrate data for packages
             where the YANG data model has changed and the automatic
             CDB upgrade is not sufficient. The upgrade component
             consists of either a Java class with a main method or a
             Python class with an upgrade method, that is expected to
             run one time only.";
          container upgrade {
            choice type {
              // NCS drop mandatory statement
              case java {
                leaf java-class-name {
                  type string;
                  description
                    "The name of the Java class that implements a main method
                     which will migrate data.";
                }
              }
              case python {
                leaf python-class-name {
                  type string;
                  description
                    "Name of the Python class that implements an upgrade
                     method which will migrate data.";
                }
              }
            }
          }
        }
        case callback {
          description
            "A data-provider can be used to implement NCS,
             services, external data providers, etc.";
          container callback {
            leaf-list java-class-name {
              // NCS patched for predictable order
              ordered-by user;
              type string;
              // NCS drop min-elements statement
              description
                "The name of the Java class that is annotated with one of
                 the callback annotations 'ServiceCallback', 'ActionCallback',
                 'AuthCallback', 'DataCallback', 'DBCallback',
                 'SnmpInformResponseCallback', 'TransCallback',
                 'TransValidateCallback', or 'ValidateCallback'.";
            }
          }
        }
        case application {
          description
            "An application is a generic type with some
             Java code, and a Java class that is instantiated by NCS.";
          container application {
            choice type {
              // NCS drop mandatory statement
              case java {
                description
                  "Java application";
                leaf java-class-name {
                  type string;
                  // NCS drop mandatory statement
                  description
                    "The name of the Java class that implements the
                     interface 'com.tailf.ncs.ApplicationComponent'.";
                }
              }
              case python {
                description
                  "Python application";
                leaf python-class-name {
                  type string;
                  // NCS drop mandatory statement
                  description
                    "The name of the Python class that will be started by NCS.

                     An empty string here indicates a Python Library,
                     i.e., no code will be invoked by NCS. However, other
                     packages may depend on this package, thus getting the
                     PYTHONPATH setup to point to this package.";
                }
              }
            }
            leaf start-phase {
              type string;
              // NCS drop default statement
              description
                "The start phase where the package is instantiated.";
            }
          }
        }
      }
    }
  }

  grouping ncs_template_reload-params {
    leaf max-wait-time {
      type string;
      units "seconds";
      // NCS drop default statement
      description
        "When a reload includes updated YANG code (.fxs files) or
         CLI specification files (.ccl files), NCS needs to run
         a data model upgrade procedure. This requires that all
         transactions are closed, in particular that users having
         CLI sessions in configure mode must exit to operational
         mode. The 'max-wait-time' is the maximum time to wait for
         this to complete.";
    }
    leaf timeout-action {
      type string;
      // NCS drop default statement
      description
        "If 'max-wait-time' is reached with transactions still open,
         the reload will be canceled if 'timeout-action' is 'fail'.
         If 'timeout-action' is 'kill', any remaining transactions
         will instead be forcibly terminated, and the reload will
         proceed.";
    }
    leaf force {
      description
        "If this parameter is not given, then the action may abort if
         some dangerous operations need to be performed, such as removal of
         the whole namespace. By using this parameter the operator
         acknowledges this, and allows to proceed with the dangerous
         operations.";
      type empty;
    }
    leaf wait-commit-queue-empty {
      type empty;
      description
        "If the reload includes updated YANG code (.fxs files) or CLI
         specification files (.ccl files), it will block new transactions
         and wait for all the ongoing queue items to finish. The reload
         proceeds when the commit queue becomes empty. Otherwise, it will
         stop with an error.";
    }
  }

  grouping ncs_rpc_notif_package-meta-data {
    description
      "This grouping describes meta-data for a NCS package.

       A NCS package has the following file structure:

         <package-name>/package-meta-data.xml
                        load-dir/
                        cdb/
                        shared-jar/
                        private-jar/
                        erlang-lib/
                        python/
                        webui/
                        templates/
                        scripts/
                        src/
                        doc/
                        netsim/

       The package-meta-data.xml file contains a top-level element
       'ncs-package' in the namespace defined by this module, which
       behaves as if defined as:

         container ncs-package {
           uses package-meta-data;
         }

       The optional 'load-dir' directory is appended to the
       'load-path' of NCS.  It contains fxs files and ccl files
       etc. It can also contain .xml files, which will be loaded by
       CDB during init and upgrade (i.e. these files can be used to
       include inital CDB data needed by the package).

       The optional 'shared-jar' directory contains jar files with
       Java code that is shared among all packages. Once loaded, this
       code cannot be modified without reloading all jar files for all
       packages.

       The optional 'private-jar' directory contains jar files with
       Java code that are loaded by a package-spefic class loader.
       Thus, this code is not available from other packages.  By
       putting for example the code for a specific service in a
       private jar, NCS can dynamically upgrade the service without
       affecting any other service.

       The optional 'erlang-lib' directory contains Erlang
       applications.

       The optional 'python' directory contains Python code for the
       component.

       The optional 'webui' directory contains webui customization
       files.

       The optional 'templates' directory contains templates for
       template-based services.";

    typedef version {
      type ncs_rpc_notif_package-version;
      description
        "The version is a sequence of numbers and words, separated by '.'
         or '-'.  When NCS compares a version string, it parses the string
         into the sequence of numbers and words, and compares each component
         individually.";
    }
    leaf name {
      tailf:info
        "A unique name, used to identify the package";
      type string;
      mandatory true;
      description
        "A unique name, used to identify the package.";
    }
    leaf package-version {
      tailf:info
        "The version of the package";
      type version;
      mandatory true;
      description
        "The version of the package. An NCS customer that modifies a package
         is encouraged to add its own info to this string, e.g.
           1.2-acme-1
           1.2-acme-2";
    }
    leaf description {
      tailf:info
        "Free-form text describing the package";
      type string;
      description
        "Free-form text describing the package.";
    }
    leaf-list ncs-min-version {
      tailf:info
        "Minimum NCS versions, one per NCS major,  required by this package";
      type version;
      description
        "Minimum NCS versions, one per NCS major, required by this package.";
    }
    leaf-list ncs-max-version {
      tailf:info
        "Maximum NCS versions, one per NCS major,  required by this package";
      type version;
      description
        "Maximum NCS versions, one per NCS major, required by this package.";
    }
    container python-package {
      tailf:info
        "Python specific data.";
      presence "Python specific package data";
      leaf vm-name {
        type string;
        when "../callpoint-model = 'threading'" {
          tailf:xpath-root 3;
        }
        description
          "A Python package will per default run in a seperate Python VM.
           This Python VM will get a symbolic name (for reference from
           within NCS) which per default is the package 'name'.

           However, by setting 'vm-name', its value will be used as as
           the symbolic name for the Python VM started. This will
           cause packages with the same 'vm-name' to run in the same
           Python VM.";
      }
      leaf callpoint-model {
        type enumeration {
          enum "threading";
          enum "multiprocessing";
        }
        default "threading";
        description
          "A Python package will per default run all Services, Nano Services
           and Actions in the same OS process. If this is set to multiprocessing
           a separate worker process will be created for each Service,
           Nano Service and Action.

           In parallel workloads the multiprocessing callpoint model
           can improve the performance of the services";
      }
    }
    leaf directory {
      tailf:info
        "The path to the directory of the package";
      type string;
      description
        "The path to the directory of the package.";
    }
    leaf-list templates {
      tailf:info
        "The templates defined by this package";
      type string;
      description
        "The templates defined by this package.";
    }
    leaf template-loading-mode {
      type enumeration {
        enum "strict";
        enum "relaxed";
      }
      description
        "This leaf indicates whether the templates in this package are
         interpreted in strict mode or relaxed mode. It is unset if the package
         has no templates.

         Strict mode means we report all schema-related errors in templates
         that can be identified at load time (such as unknown namespace, schema
         ambiguity or unknown ned-id). Strict mode is applid when there are no
         supported-ned-ids declared or when all of the supported-ned-ids are
         loaded.

         If the package declares supported-ned-ids, but some of them are not
         recognized, then we assume relaxed mode as we will not be able to
         identify some of the schema-related errors, for example we might need
         to skip over tags in unknown namespaces because they might belong
         to the missing ned-ids that the package supports, but that are
         currently not loaded in the runtime system.

         It is important that the package developer tests the package with
         all the supported-ned-ids loaded, i.e. in strict mode, as it helps
         catch errors that may be ignored in relaxed mode.";
    }
    leaf-list supported-ned-id {
      tailf:info
        "The list of ned-ids supported by this package";
      type union {
        // NCS patched to string, due to LSA partial NED
        type string;
        type string;
      }
      description
        "Templates defined by this package will be applied in the scope of
         this list of ned-ids. Trying to apply a template defined by this
         package to a device with a different ned-id will result at runtime
         error. If no supported-ned-id is defined, then no such restrictions
         are placed on this package's templates, however it may lead to a
         situation where loading an additional NED can prevent the package
         defining the template from loading by making a template ambiguous.

         This parameter has no effect for packages that define no templates.";
    }
    leaf-list supported-ned-id-match {
      tailf:info
        "List of regexes for ned-ids supported by this package";
      type string;
      description
        "This list is used to populate 'supported-ned-id' with the help
         of regular expressions. Ned-ids in the system that match at least
         one of the regular expressions in this list are added to the
         'supported-ned-id' list.";
    }
    list required-package {
      tailf:info
        "A list of packages required by this package";
      key "name";
      description
        "A list of packages required by this package.  NCS will not
         load any package with missing dependencies.";
      leaf name {
        tailf:info
          "Required package name";
        type string;
      }
      leaf min-version {
        tailf:info
          "Required package minimum version";
        type version;
        description
          "Minimum version required by this package.";
      }
      leaf max-version {
        tailf:info
          "Required package maximum version";
        type version;
        description
          "Maximum version required by this package.";
      }
    }
    list component {
      tailf:info
        "Package components";
      key "name";
      leaf name {
        tailf:info
          "Component name";
        type string;
        description
          "A unique name, used to identify the component within
           the package.";
      }
      leaf description {
        tailf:info
          "Free-form text describing the component";
        type string;
        description
          "Free-form text describing the component.";
      }
      leaf entitlement-tag {
        tailf:info
          "Entitlement tag for Smart Licensing.";
        type string;
        description
          "Identifies the component for Smart Licensing.";
      }
      choice type {
        mandatory true;
        case ned {
          description
            "A NED package typically contains the YANG models for
             the device, and Java classes derived from these modules.
             The Java classes are delivered as 'shared' jar files, which
             makes them available for Java services and other Java code
             to use.";
          container ned {
            tailf:info
              "NED component";
            choice ned-type {
              mandatory true;
              container netconf {
                tailf:info
                  "NETCONF NED";
                description
                  "A NETCONF NED typically consists of the YANG modules
                   for the device, and Java classes derived from these
                   modules.";
                leaf ned-id {
                  tailf:info
                    "The NETCONF NED identity";
                  // NCS patched to string, due to LSA partial NED
                  type string;
                  mandatory false;
                  description
                    "The identity that identifies the NETCONF NED. If
                     let empty it is just a plain NETCONF NED.";
                }
              }
              container snmp {
                tailf:info
                  "SNMP NED";
                description
                  "An SNMP NED typically consists of the MIB modules
                   for the device, YANG modules derived from the MIBs, and
                   Java classes derived from these models.";
                leaf ned-id {
                  tailf:info
                    "The SNMP NED identity";
                  // NCS patched to string, due to LSA partial NED
                  type string;
                  description
                    "The identity that identifies the SNMP NED.";
                }
              }
              container cli {
                tailf:info
                  "CLI NED";
                description
                  "A CLI NED typically consists of YANG models for the
                   device, Java classes derived from these modules, and
                   a Java class responsible for the communication with the
                   device.";
                leaf ned-id {
                  tailf:info
                    "The CLI NED identity";
                  // NCS patched to string, due to LSA partial NED
                  type string;
                  mandatory true;
                  description
                    "The identity that identifies the CLI NED.  All
                     devices of type 'cli' that are configured with
                     this 'ned-id' are handled by this compontent's 'NedCli'
                     Java class.";
                }
                leaf java-class-name {
                  tailf:info
                    "Name of the Java class that implements the NED";
                  type string;
                  mandatory true;
                  description
                    "The name of the Java class that implements the
                     interface 'NedCli'.";
                }
              }
              container generic {
                tailf:info
                  "Generic NED";
                description
                  "A Generic NED typically consists of YANG models for the
                   device, Java classes derived from these modules, and
                   a Java class responsible for the communication with the
                   device.";
                leaf ned-id {
                  tailf:info
                    "The Generic NED identity";
                  // NCS patched to string, due to LSA partial NED
                  type string;
                  mandatory true;
                  description
                    "The identity that identifies the Generic NED.  All
                     devices of type 'generic' that are configured with
                     this 'ned-id' are handled by this component's 'NedGeneric'
                     Java class.";
                }
                leaf java-class-name {
                  tailf:info
                    "Name of the Java class that implements the NED";
                  type string;
                  mandatory true;
                  description
                    "The name of the Java class that implements the
                     interface 'NedGeneric'.";
                }
              }
            }
            container device {
              tailf:info
                "NED device type information";
              leaf vendor {
                tailf:info
                  "Vendor name";
                type string;
                mandatory true;
                description
                  "Free-form string, used for documentation purposes.";
              }
              leaf product-family {
                tailf:info
                  "Product family";
                type string;
                description
                  "The product-specific family of products supported by this
                   NED.

                   In some cases, this could be as generic as 'ios', if the
                   NED works with any ios release.  In other cases it could
                   be as specific as 'ios-11.4' if it works only with ios
                   release 11.4.  And in some cases, it would be some middle
                   ground, e.g., 'ios-11' or 'ios-11+'.";
              }
            }
            list option {
              tailf:info
                "NED specific options";
              key "name";
              description
                "A list of options to configure the behavior of this NED.
                 Available options are:

                  ordered-diff (for generic NEDs),
                     Order the operations sent the NED such that
                     dependencies are taken into account, ie if a
                     list element is deleted and there are leafref
                     references to the instance, order the leafref
                     in front of the delete of the instance.

                  show-tag (for CLI NEDs)
                     If set the NED will only ask for one top-tag in
                     the show() callback instead of invoking the show()
                     callback once for each top-tag. Many NEDs return
                     the entire configuration in one go and are only
                     interested in one show() invocation. The common
                     workaround is to only return when the show() command
                     is invoked with a specific top-tag, and return the
                     empty string for the rest. With this option set
                     there will only be one show() invocation.

                  allow-abbrevs (for CLI NEDs)
                     When set abbreviated commands are allowed to be
                     sent in the response to the show() callback. Devices
                     typically do not generate abbreviated commands and
                     setting the above option may introduce ambiguity in
                     the parsing.

                  show-partial
                    Set if the NED supports partial show.
                ";
              leaf name {
                tailf:info
                  "Option name";
                type string;
              }
              leaf value {
                tailf:info
                  "Option value";
                type string;
              }
            }
          }
        }
        case upgrade {
          description
            "An upgrade component is used to migrate data for packages
             where the YANG data model has changed and the automatic
             CDB upgrade is not sufficient. The upgrade component
             consists of either a Java class with a main method or a
             Python class with an upgrade method, that is expected to
             run one time only.";
          container upgrade {
            tailf:info
              "Upgrade component information";
            choice type {
              mandatory true;
              case java {
                leaf java-class-name {
                  tailf:info
                    "Name of the Java class that implements
                     the data migration";
                  type string;
                  description
                    "The name of the Java class that implements a main method
                     which will migrate data.";
                }
              }
              case python {
                leaf python-class-name {
                  tailf:info
                    "Name of the Python class that implements
                     the data migration";
                  type string;
                  description
                    "Name of the Python class that implements an upgrade
                     method which will migrate data.";
                }
              }
            }
          }
        }
        case callback {
          description
            "A data-provider can be used to implement NCS,
             services, external data providers, etc.";
          container callback {
            tailf:info
              "Callback component";
            leaf-list java-class-name {
              tailf:info
                "Java classes that implement the callback";
              type string;
              min-elements 1;
              description
                "The name of the Java class that is annotated with one of
                 the callback annotations 'ServiceCallback', 'ActionCallback',
                 'AuthCallback', 'DataCallback', 'DBCallback',
                 'SnmpInformResponseCallback', 'TransCallback',
                 'TransValidateCallback', or 'ValidateCallback'.";
            }
          }
        }
        case application {
          description
            "An application is a generic type with some
             Java code, and a Java class that is instantiated by NCS.";
          container application {
            tailf:info
              "Application component";
            choice type {
              mandatory true;
              case java {
                description
                  "Java application";
                leaf java-class-name {
                  tailf:info
                    "Java class that implements the application";
                  type string;
                  mandatory true;
                  description
                    "The name of the Java class that implements the
                     interface 'com.tailf.ncs.ApplicationComponent'.";
                }
              }
              case python {
                description
                  "Python application";
                leaf python-class-name {
                  tailf:info
                    "Python class that implements the application";
                  type string;
                  mandatory true;
                  description
                    "The name of the Python class that will be started by NCS.

                     An empty string here indicates a Python Library,
                     i.e., no code will be invoked by NCS. However, other
                     packages may depend on this package, thus getting the
                     PYTHONPATH setup to point to this package.";
                }
              }
            }
            leaf start-phase {
              tailf:info
                "NCS start phase where the package is instantiated";
              type enumeration {
                enum "phase1";
                enum "phase2";
              }
              default "phase2";
              description
                "The start phase where the package is instantiated.";
            }
          }
        }
      }
    }
  }

  grouping ncs_rpc_notif_reload-params {
    leaf max-wait-time {
      tailf:info
        "Max time in seconds to wait for commit queue to become empty
         (if 'wait-for-commit-queue-empty' parameter is set) and
         transactions to close";
      type uint32 {
        range "0..4294967";
      }
      units "seconds";
      default "10";
      description
        "When a reload includes updated YANG code (.fxs files) or
         CLI specification files (.ccl files), NCS needs to run
         a data model upgrade procedure. This requires that all
         transactions are closed, in particular that users having
         CLI sessions in configure mode must exit to operational
         mode. The 'max-wait-time' is the maximum time to wait for
         this to complete.";
    }
    leaf timeout-action {
      tailf:info
        "Action taken when max-wait-time is reached";
      type enumeration {
        enum "fail" {
          tailf:info
            "Package reload is canceled";
        }
        enum "kill" {
          tailf:info
            "Open transactions are forcibly terminated";
        }
      }
      default "fail";
      description
        "If 'max-wait-time' is reached with transactions still open,
         the reload will be canceled if 'timeout-action' is 'fail'.
         If 'timeout-action' is 'kill', any remaining transactions
         will instead be forcibly terminated, and the reload will
         proceed.";
    }
    leaf force {
      tailf:info
        "Ignore warnings.";
      description
        "If this parameter is not given, then the action may abort if
         some dangerous operations need to be performed, such as removal of
         the whole namespace. By using this parameter the operator
         acknowledges this, and allows to proceed with the dangerous
         operations.";
      type empty;
    }
    leaf wait-commit-queue-empty {
      type empty;
      tailf:info
        "Enable waiting for commit queue to become empty";
      description
        "If the reload includes updated YANG code (.fxs files) or CLI
         specification files (.ccl files), it will block new transactions
         and wait for all the ongoing queue items to finish. The reload
         proceeds when the commit queue becomes empty. Otherwise, it will
         stop with an error.";
    }
  }

  grouping live_ncs_package-meta-data {
    description
      "This grouping describes meta-data for a NCS package.

       A NCS package has the following file structure:

         <package-name>/package-meta-data.xml
                        load-dir/
                        cdb/
                        shared-jar/
                        private-jar/
                        erlang-lib/
                        python/
                        webui/
                        templates/
                        scripts/
                        src/
                        doc/
                        netsim/

       The package-meta-data.xml file contains a top-level element
       'ncs-package' in the namespace defined by this module, which
       behaves as if defined as:

         container ncs-package {
           uses package-meta-data;
         }

       The optional 'load-dir' directory is appended to the
       'load-path' of NCS.  It contains fxs files and ccl files
       etc. It can also contain .xml files, which will be loaded by
       CDB during init and upgrade (i.e. these files can be used to
       include inital CDB data needed by the package).

       The optional 'shared-jar' directory contains jar files with
       Java code that is shared among all packages. Once loaded, this
       code cannot be modified without reloading all jar files for all
       packages.

       The optional 'private-jar' directory contains jar files with
       Java code that are loaded by a package-spefic class loader.
       Thus, this code is not available from other packages.  By
       putting for example the code for a specific service in a
       private jar, NCS can dynamically upgrade the service without
       affecting any other service.

       The optional 'erlang-lib' directory contains Erlang
       applications.

       The optional 'python' directory contains Python code for the
       component.

       The optional 'webui' directory contains webui customization
       files.

       The optional 'templates' directory contains templates for
       template-based services.";

    typedef version {
      type live_ncs_package-version;
      description
        "The version is a sequence of numbers and words, separated by '.'
         or '-'.  When NCS compares a version string, it parses the string
         into the sequence of numbers and words, and compares each component
         individually.";
    }
    leaf name {
      tailf:info
        "A unique name, used to identify the package";
      type string;
      // NCS drop mandatory statement
      description
        "A unique name, used to identify the package.";
    }
    leaf package-version {
      tailf:info
        "The version of the package";
      type version;
      // NCS drop mandatory statement
      description
        "The version of the package. An NCS customer that modifies a package
         is encouraged to add its own info to this string, e.g.
           1.2-acme-1
           1.2-acme-2";
    }
    leaf description {
      tailf:info
        "Free-form text describing the package";
      type string;
      description
        "Free-form text describing the package.";
    }
    leaf-list ncs-min-version {
      tailf:info
        "Minimum NCS versions, one per NCS major,  required by this package";
      type version;
      description
        "Minimum NCS versions, one per NCS major, required by this package.";
    }
    leaf-list ncs-max-version {
      tailf:info
        "Maximum NCS versions, one per NCS major,  required by this package";
      type version;
      description
        "Maximum NCS versions, one per NCS major, required by this package.";
    }
    container python-package {
      tailf:info
        "Python specific data.";
      presence "Python specific package data";
      leaf vm-name {
        type string;
        // NCS drop when statement
        description
          "A Python package will per default run in a seperate Python VM.
           This Python VM will get a symbolic name (for reference from
           within NCS) which per default is the package 'name'.

           However, by setting 'vm-name', its value will be used as as
           the symbolic name for the Python VM started. This will
           cause packages with the same 'vm-name' to run in the same
           Python VM.";
      }
      leaf callpoint-model {
        type enumeration {
          enum "threading";
          enum "multiprocessing";
        }
        // NCS drop default statement
        description
          "A Python package will per default run all Services, Nano Services
           and Actions in the same OS process. If this is set to multiprocessing
           a separate worker process will be created for each Service,
           Nano Service and Action.

           In parallel workloads the multiprocessing callpoint model
           can improve the performance of the services";
      }
    }
    leaf directory {
      tailf:info
        "The path to the directory of the package";
      type string;
      description
        "The path to the directory of the package.";
    }
    leaf-list templates {
      tailf:info
        "The templates defined by this package";
      type string;
      description
        "The templates defined by this package.";
    }
    leaf template-loading-mode {
      type enumeration {
        enum "strict";
        enum "relaxed";
      }
      description
        "This leaf indicates whether the templates in this package are
         interpreted in strict mode or relaxed mode. It is unset if the package
         has no templates.

         Strict mode means we report all schema-related errors in templates
         that can be identified at load time (such as unknown namespace, schema
         ambiguity or unknown ned-id). Strict mode is applid when there are no
         supported-ned-ids declared or when all of the supported-ned-ids are
         loaded.

         If the package declares supported-ned-ids, but some of them are not
         recognized, then we assume relaxed mode as we will not be able to
         identify some of the schema-related errors, for example we might need
         to skip over tags in unknown namespaces because they might belong
         to the missing ned-ids that the package supports, but that are
         currently not loaded in the runtime system.

         It is important that the package developer tests the package with
         all the supported-ned-ids loaded, i.e. in strict mode, as it helps
         catch errors that may be ignored in relaxed mode.";
    }
    leaf-list supported-ned-id {
      tailf:info
        "The list of ned-ids supported by this package";
      type union {
        // NCS patched to string, due to LSA partial NED
        type string;
        type string;
      }
      description
        "Templates defined by this package will be applied in the scope of
         this list of ned-ids. Trying to apply a template defined by this
         package to a device with a different ned-id will result at runtime
         error. If no supported-ned-id is defined, then no such restrictions
         are placed on this package's templates, however it may lead to a
         situation where loading an additional NED can prevent the package
         defining the template from loading by making a template ambiguous.

         This parameter has no effect for packages that define no templates.";
    }
    leaf-list supported-ned-id-match {
      tailf:info
        "List of regexes for ned-ids supported by this package";
      type string;
      description
        "This list is used to populate 'supported-ned-id' with the help
         of regular expressions. Ned-ids in the system that match at least
         one of the regular expressions in this list are added to the
         'supported-ned-id' list.";
    }
    list required-package {
      tailf:info
        "A list of packages required by this package";
      key "name";
      description
        "A list of packages required by this package.  NCS will not
         load any package with missing dependencies.";
      leaf name {
        tailf:info
          "Required package name";
        type string;
      }
      leaf min-version {
        tailf:info
          "Required package minimum version";
        type version;
        description
          "Minimum version required by this package.";
      }
      leaf max-version {
        tailf:info
          "Required package maximum version";
        type version;
        description
          "Maximum version required by this package.";
      }
    }
    list component {
      tailf:info
        "Package components";
      key "name";
      leaf name {
        tailf:info
          "Component name";
        type string;
        description
          "A unique name, used to identify the component within
           the package.";
      }
      leaf description {
        tailf:info
          "Free-form text describing the component";
        type string;
        description
          "Free-form text describing the component.";
      }
      leaf entitlement-tag {
        tailf:info
          "Entitlement tag for Smart Licensing.";
        type string;
        description
          "Identifies the component for Smart Licensing.";
      }
      choice type {
        // NCS drop mandatory statement
        case ned {
          description
            "A NED package typically contains the YANG models for
             the device, and Java classes derived from these modules.
             The Java classes are delivered as 'shared' jar files, which
             makes them available for Java services and other Java code
             to use.";
          container ned {
            tailf:info
              "NED component";
            choice ned-type {
              // NCS drop mandatory statement
              container netconf {
                tailf:info
                  "NETCONF NED";
                description
                  "A NETCONF NED typically consists of the YANG modules
                   for the device, and Java classes derived from these
                   modules.";
                leaf ned-id {
                  tailf:info
                    "The NETCONF NED identity";
                  // NCS patched to string, due to LSA partial NED
                  type string;
                  // NCS drop mandatory statement
                  description
                    "The identity that identifies the NETCONF NED. If
                     let empty it is just a plain NETCONF NED.";
                }
              }
              container snmp {
                tailf:info
                  "SNMP NED";
                description
                  "An SNMP NED typically consists of the MIB modules
                   for the device, YANG modules derived from the MIBs, and
                   Java classes derived from these models.";
                leaf ned-id {
                  tailf:info
                    "The SNMP NED identity";
                  // NCS patched to string, due to LSA partial NED
                  type string;
                  description
                    "The identity that identifies the SNMP NED.";
                }
              }
              container cli {
                tailf:info
                  "CLI NED";
                description
                  "A CLI NED typically consists of YANG models for the
                   device, Java classes derived from these modules, and
                   a Java class responsible for the communication with the
                   device.";
                leaf ned-id {
                  tailf:info
                    "The CLI NED identity";
                  // NCS patched to string, due to LSA partial NED
                  type string;
                  // NCS drop mandatory statement
                  description
                    "The identity that identifies the CLI NED.  All
                     devices of type 'cli' that are configured with
                     this 'ned-id' are handled by this compontent's 'NedCli'
                     Java class.";
                }
                leaf java-class-name {
                  tailf:info
                    "Name of the Java class that implements the NED";
                  type string;
                  // NCS drop mandatory statement
                  description
                    "The name of the Java class that implements the
                     interface 'NedCli'.";
                }
              }
              container generic {
                tailf:info
                  "Generic NED";
                description
                  "A Generic NED typically consists of YANG models for the
                   device, Java classes derived from these modules, and
                   a Java class responsible for the communication with the
                   device.";
                leaf ned-id {
                  tailf:info
                    "The Generic NED identity";
                  // NCS patched to string, due to LSA partial NED
                  type string;
                  // NCS drop mandatory statement
                  description
                    "The identity that identifies the Generic NED.  All
                     devices of type 'generic' that are configured with
                     this 'ned-id' are handled by this component's 'NedGeneric'
                     Java class.";
                }
                leaf java-class-name {
                  tailf:info
                    "Name of the Java class that implements the NED";
                  type string;
                  // NCS drop mandatory statement
                  description
                    "The name of the Java class that implements the
                     interface 'NedGeneric'.";
                }
              }
            }
            container device {
              tailf:info
                "NED device type information";
              leaf vendor {
                tailf:info
                  "Vendor name";
                type string;
                // NCS drop mandatory statement
                description
                  "Free-form string, used for documentation purposes.";
              }
              leaf product-family {
                tailf:info
                  "Product family";
                type string;
                description
                  "The product-specific family of products supported by this
                   NED.

                   In some cases, this could be as generic as 'ios', if the
                   NED works with any ios release.  In other cases it could
                   be as specific as 'ios-11.4' if it works only with ios
                   release 11.4.  And in some cases, it would be some middle
                   ground, e.g., 'ios-11' or 'ios-11+'.";
              }
            }
            list option {
              tailf:info
                "NED specific options";
              key "name";
              description
                "A list of options to configure the behavior of this NED.
                 Available options are:

                  ordered-diff (for generic NEDs),
                     Order the operations sent the NED such that
                     dependencies are taken into account, ie if a
                     list element is deleted and there are leafref
                     references to the instance, order the leafref
                     in front of the delete of the instance.

                  show-tag (for CLI NEDs)
                     If set the NED will only ask for one top-tag in
                     the show() callback instead of invoking the show()
                     callback once for each top-tag. Many NEDs return
                     the entire configuration in one go and are only
                     interested in one show() invocation. The common
                     workaround is to only return when the show() command
                     is invoked with a specific top-tag, and return the
                     empty string for the rest. With this option set
                     there will only be one show() invocation.

                  allow-abbrevs (for CLI NEDs)
                     When set abbreviated commands are allowed to be
                     sent in the response to the show() callback. Devices
                     typically do not generate abbreviated commands and
                     setting the above option may introduce ambiguity in
                     the parsing.

                  show-partial
                    Set if the NED supports partial show.
                ";
              leaf name {
                tailf:info
                  "Option name";
                type string;
              }
              leaf value {
                tailf:info
                  "Option value";
                type string;
              }
            }
          }
        }
        case upgrade {
          description
            "An upgrade component is used to migrate data for packages
             where the YANG data model has changed and the automatic
             CDB upgrade is not sufficient. The upgrade component
             consists of either a Java class with a main method or a
             Python class with an upgrade method, that is expected to
             run one time only.";
          container upgrade {
            tailf:info
              "Upgrade component information";
            choice type {
              // NCS drop mandatory statement
              case java {
                leaf java-class-name {
                  tailf:info
                    "Name of the Java class that implements
                     the data migration";
                  type string;
                  description
                    "The name of the Java class that implements a main method
                     which will migrate data.";
                }
              }
              case python {
                leaf python-class-name {
                  tailf:info
                    "Name of the Python class that implements
                     the data migration";
                  type string;
                  description
                    "Name of the Python class that implements an upgrade
                     method which will migrate data.";
                }
              }
            }
          }
        }
        case callback {
          description
            "A data-provider can be used to implement NCS,
             services, external data providers, etc.";
          container callback {
            tailf:info
              "Callback component";
            leaf-list java-class-name {
              tailf:info
                "Java classes that implement the callback";
              type string;
              // NCS drop min-elements statement
              description
                "The name of the Java class that is annotated with one of
                 the callback annotations 'ServiceCallback', 'ActionCallback',
                 'AuthCallback', 'DataCallback', 'DBCallback',
                 'SnmpInformResponseCallback', 'TransCallback',
                 'TransValidateCallback', or 'ValidateCallback'.";
            }
          }
        }
        case application {
          description
            "An application is a generic type with some
             Java code, and a Java class that is instantiated by NCS.";
          container application {
            tailf:info
              "Application component";
            choice type {
              // NCS drop mandatory statement
              case java {
                description
                  "Java application";
                leaf java-class-name {
                  tailf:info
                    "Java class that implements the application";
                  type string;
                  // NCS drop mandatory statement
                  description
                    "The name of the Java class that implements the
                     interface 'com.tailf.ncs.ApplicationComponent'.";
                }
              }
              case python {
                description
                  "Python application";
                leaf python-class-name {
                  tailf:info
                    "Python class that implements the application";
                  type string;
                  // NCS drop mandatory statement
                  description
                    "The name of the Python class that will be started by NCS.

                     An empty string here indicates a Python Library,
                     i.e., no code will be invoked by NCS. However, other
                     packages may depend on this package, thus getting the
                     PYTHONPATH setup to point to this package.";
                }
              }
            }
            leaf start-phase {
              tailf:info
                "NCS start phase where the package is instantiated";
              type enumeration {
                enum "phase1";
                enum "phase2";
              }
              // NCS drop default statement
              description
                "The start phase where the package is instantiated.";
            }
          }
        }
      }
    }
  }

  grouping live_ncs_reload-params {
    leaf max-wait-time {
      tailf:info
        "Max time in seconds to wait for commit queue to become empty
         (if 'wait-for-commit-queue-empty' parameter is set) and
         transactions to close";
      type uint32 {
        range "0..4294967";
      }
      units "seconds";
      // NCS drop default statement
      description
        "When a reload includes updated YANG code (.fxs files) or
         CLI specification files (.ccl files), NCS needs to run
         a data model upgrade procedure. This requires that all
         transactions are closed, in particular that users having
         CLI sessions in configure mode must exit to operational
         mode. The 'max-wait-time' is the maximum time to wait for
         this to complete.";
    }
    leaf timeout-action {
      tailf:info
        "Action taken when max-wait-time is reached";
      type enumeration {
        enum "fail" {
          tailf:info
            "Package reload is canceled";
        }
        enum "kill" {
          tailf:info
            "Open transactions are forcibly terminated";
        }
      }
      // NCS drop default statement
      description
        "If 'max-wait-time' is reached with transactions still open,
         the reload will be canceled if 'timeout-action' is 'fail'.
         If 'timeout-action' is 'kill', any remaining transactions
         will instead be forcibly terminated, and the reload will
         proceed.";
    }
    leaf force {
      tailf:info
        "Ignore warnings.";
      description
        "If this parameter is not given, then the action may abort if
         some dangerous operations need to be performed, such as removal of
         the whole namespace. By using this parameter the operator
         acknowledges this, and allows to proceed with the dangerous
         operations.";
      type empty;
    }
    leaf wait-commit-queue-empty {
      type empty;
      tailf:info
        "Enable waiting for commit queue to become empty";
      description
        "If the reload includes updated YANG code (.fxs files) or CLI
         specification files (.ccl files), it will block new transactions
         and wait for all the ongoing queue items to finish. The reload
         proceeds when the commit queue becomes empty. Otherwise, it will
         stop with an error.";
    }
  }

  grouping package-meta-data {
    description
      "This grouping describes meta-data for a NCS package.

       A NCS package has the following file structure:

         <package-name>/package-meta-data.xml
                        load-dir/
                        cdb/
                        shared-jar/
                        private-jar/
                        erlang-lib/
                        python/
                        webui/
                        templates/
                        scripts/
                        src/
                        doc/
                        netsim/

       The package-meta-data.xml file contains a top-level element
       'ncs-package' in the namespace defined by this module, which
       behaves as if defined as:

         container ncs-package {
           uses package-meta-data;
         }

       The optional 'load-dir' directory is appended to the
       'load-path' of NCS.  It contains fxs files and ccl files
       etc. It can also contain .xml files, which will be loaded by
       CDB during init and upgrade (i.e. these files can be used to
       include inital CDB data needed by the package).

       The optional 'shared-jar' directory contains jar files with
       Java code that is shared among all packages. Once loaded, this
       code cannot be modified without reloading all jar files for all
       packages.

       The optional 'private-jar' directory contains jar files with
       Java code that are loaded by a package-spefic class loader.
       Thus, this code is not available from other packages.  By
       putting for example the code for a specific service in a
       private jar, NCS can dynamically upgrade the service without
       affecting any other service.

       The optional 'erlang-lib' directory contains Erlang
       applications.

       The optional 'python' directory contains Python code for the
       component.

       The optional 'webui' directory contains webui customization
       files.

       The optional 'templates' directory contains templates for
       template-based services.";

    typedef version {
      type package-version;
      description
        "The version is a sequence of numbers and words, separated by '.'
         or '-'.  When NCS compares a version string, it parses the string
         into the sequence of numbers and words, and compares each component
         individually.";
    }
    leaf name {
      tailf:info
        "A unique name, used to identify the package";
      type string;
      mandatory true;
      description
        "A unique name, used to identify the package.";
    }
    leaf package-version {
      tailf:info
        "The version of the package";
      type version;
      mandatory true;
      description
        "The version of the package. An NCS customer that modifies a package
         is encouraged to add its own info to this string, e.g.
           1.2-acme-1
           1.2-acme-2";
    }
    leaf description {
      tailf:info
        "Free-form text describing the package";
      type string;
      description
        "Free-form text describing the package.";
    }
    leaf-list ncs-min-version {
      tailf:info
        "Minimum NCS versions, one per NCS major,  required by this package";
      type version;
      description
        "Minimum NCS versions, one per NCS major, required by this package.";
    }
    leaf-list ncs-max-version {
      tailf:info
        "Maximum NCS versions, one per NCS major,  required by this package";
      type version;
      description
        "Maximum NCS versions, one per NCS major, required by this package.";
    }
    container python-package {
      tailf:info
        "Python specific data.";
      presence "Python specific package data";
      leaf vm-name {
        type string;
        when "../callpoint-model = 'threading'" {
          tailf:xpath-root 3;
        }
        description
          "A Python package will per default run in a seperate Python VM.
           This Python VM will get a symbolic name (for reference from
           within NCS) which per default is the package 'name'.

           However, by setting 'vm-name', its value will be used as as
           the symbolic name for the Python VM started. This will
           cause packages with the same 'vm-name' to run in the same
           Python VM.";
      }
      leaf callpoint-model {
        type enumeration {
          enum "threading";
          enum "multiprocessing";
        }
        default "threading";
        description
          "A Python package will per default run all Services, Nano Services
           and Actions in the same OS process. If this is set to multiprocessing
           a separate worker process will be created for each Service,
           Nano Service and Action.

           In parallel workloads the multiprocessing callpoint model
           can improve the performance of the services";
      }
    }
    leaf directory {
      tailf:info
        "The path to the directory of the package";
      type string;
      description
        "The path to the directory of the package.";
    }
    leaf-list templates {
      tailf:info
        "The templates defined by this package";
      type string;
      description
        "The templates defined by this package.";
    }
    leaf template-loading-mode {
      type enumeration {
        enum "strict";
        enum "relaxed";
      }
      description
        "This leaf indicates whether the templates in this package are
         interpreted in strict mode or relaxed mode. It is unset if the package
         has no templates.

         Strict mode means we report all schema-related errors in templates
         that can be identified at load time (such as unknown namespace, schema
         ambiguity or unknown ned-id). Strict mode is applid when there are no
         supported-ned-ids declared or when all of the supported-ned-ids are
         loaded.

         If the package declares supported-ned-ids, but some of them are not
         recognized, then we assume relaxed mode as we will not be able to
         identify some of the schema-related errors, for example we might need
         to skip over tags in unknown namespaces because they might belong
         to the missing ned-ids that the package supports, but that are
         currently not loaded in the runtime system.

         It is important that the package developer tests the package with
         all the supported-ned-ids loaded, i.e. in strict mode, as it helps
         catch errors that may be ignored in relaxed mode.";
    }
    leaf-list supported-ned-id {
      tailf:info
        "The list of ned-ids supported by this package";
      type union {
        // NCS patched to string, due to LSA partial NED
        type string;
        type string;
      }
      description
        "Templates defined by this package will be applied in the scope of
         this list of ned-ids. Trying to apply a template defined by this
         package to a device with a different ned-id will result at runtime
         error. If no supported-ned-id is defined, then no such restrictions
         are placed on this package's templates, however it may lead to a
         situation where loading an additional NED can prevent the package
         defining the template from loading by making a template ambiguous.

         This parameter has no effect for packages that define no templates.";
    }
    leaf-list supported-ned-id-match {
      tailf:info
        "List of regexes for ned-ids supported by this package";
      type string;
      description
        "This list is used to populate 'supported-ned-id' with the help
         of regular expressions. Ned-ids in the system that match at least
         one of the regular expressions in this list are added to the
         'supported-ned-id' list.";
    }
    list required-package {
      tailf:info
        "A list of packages required by this package";
      key "name";
      description
        "A list of packages required by this package.  NCS will not
         load any package with missing dependencies.";
      leaf name {
        tailf:info
          "Required package name";
        type string;
      }
      leaf min-version {
        tailf:info
          "Required package minimum version";
        type version;
        description
          "Minimum version required by this package.";
      }
      leaf max-version {
        tailf:info
          "Required package maximum version";
        type version;
        description
          "Maximum version required by this package.";
      }
    }
    list component {
      tailf:info
        "Package components";
      key "name";
      leaf name {
        tailf:info
          "Component name";
        type string;
        description
          "A unique name, used to identify the component within
           the package.";
      }
      leaf description {
        tailf:info
          "Free-form text describing the component";
        type string;
        description
          "Free-form text describing the component.";
      }
      leaf entitlement-tag {
        tailf:info
          "Entitlement tag for Smart Licensing.";
        type string;
        description
          "Identifies the component for Smart Licensing.";
      }
      choice type {
        mandatory true;
        case ned {
          description
            "A NED package typically contains the YANG models for
             the device, and Java classes derived from these modules.
             The Java classes are delivered as 'shared' jar files, which
             makes them available for Java services and other Java code
             to use.";
          container ned {
            tailf:info
              "NED component";
            choice ned-type {
              mandatory true;
              container netconf {
                tailf:info
                  "NETCONF NED";
                description
                  "A NETCONF NED typically consists of the YANG modules
                   for the device, and Java classes derived from these
                   modules.";
                leaf ned-id {
                  tailf:info
                    "The NETCONF NED identity";
                  // NCS patched to string, due to LSA partial NED
                  type string;
                  mandatory false;
                  description
                    "The identity that identifies the NETCONF NED. If
                     let empty it is just a plain NETCONF NED.";
                }
              }
              container snmp {
                tailf:info
                  "SNMP NED";
                description
                  "An SNMP NED typically consists of the MIB modules
                   for the device, YANG modules derived from the MIBs, and
                   Java classes derived from these models.";
                leaf ned-id {
                  tailf:info
                    "The SNMP NED identity";
                  // NCS patched to string, due to LSA partial NED
                  type string;
                  description
                    "The identity that identifies the SNMP NED.";
                }
              }
              container cli {
                tailf:info
                  "CLI NED";
                description
                  "A CLI NED typically consists of YANG models for the
                   device, Java classes derived from these modules, and
                   a Java class responsible for the communication with the
                   device.";
                leaf ned-id {
                  tailf:info
                    "The CLI NED identity";
                  // NCS patched to string, due to LSA partial NED
                  type string;
                  mandatory true;
                  description
                    "The identity that identifies the CLI NED.  All
                     devices of type 'cli' that are configured with
                     this 'ned-id' are handled by this compontent's 'NedCli'
                     Java class.";
                }
                leaf java-class-name {
                  tailf:info
                    "Name of the Java class that implements the NED";
                  type string;
                  mandatory true;
                  description
                    "The name of the Java class that implements the
                     interface 'NedCli'.";
                }
              }
              container generic {
                tailf:info
                  "Generic NED";
                description
                  "A Generic NED typically consists of YANG models for the
                   device, Java classes derived from these modules, and
                   a Java class responsible for the communication with the
                   device.";
                leaf ned-id {
                  tailf:info
                    "The Generic NED identity";
                  // NCS patched to string, due to LSA partial NED
                  type string;
                  mandatory true;
                  description
                    "The identity that identifies the Generic NED.  All
                     devices of type 'generic' that are configured with
                     this 'ned-id' are handled by this component's 'NedGeneric'
                     Java class.";
                }
                leaf java-class-name {
                  tailf:info
                    "Name of the Java class that implements the NED";
                  type string;
                  mandatory true;
                  description
                    "The name of the Java class that implements the
                     interface 'NedGeneric'.";
                }
              }
            }
            container device {
              tailf:info
                "NED device type information";
              leaf vendor {
                tailf:info
                  "Vendor name";
                type string;
                mandatory true;
                description
                  "Free-form string, used for documentation purposes.";
              }
              leaf product-family {
                tailf:info
                  "Product family";
                type string;
                description
                  "The product-specific family of products supported by this
                   NED.

                   In some cases, this could be as generic as 'ios', if the
                   NED works with any ios release.  In other cases it could
                   be as specific as 'ios-11.4' if it works only with ios
                   release 11.4.  And in some cases, it would be some middle
                   ground, e.g., 'ios-11' or 'ios-11+'.";
              }
            }
            list option {
              tailf:info
                "NED specific options";
              key "name";
              description
                "A list of options to configure the behavior of this NED.
                 Available options are:

                  ordered-diff (for generic NEDs),
                     Order the operations sent the NED such that
                     dependencies are taken into account, ie if a
                     list element is deleted and there are leafref
                     references to the instance, order the leafref
                     in front of the delete of the instance.

                  show-tag (for CLI NEDs)
                     If set the NED will only ask for one top-tag in
                     the show() callback instead of invoking the show()
                     callback once for each top-tag. Many NEDs return
                     the entire configuration in one go and are only
                     interested in one show() invocation. The common
                     workaround is to only return when the show() command
                     is invoked with a specific top-tag, and return the
                     empty string for the rest. With this option set
                     there will only be one show() invocation.

                  allow-abbrevs (for CLI NEDs)
                     When set abbreviated commands are allowed to be
                     sent in the response to the show() callback. Devices
                     typically do not generate abbreviated commands and
                     setting the above option may introduce ambiguity in
                     the parsing.

                  show-partial
                    Set if the NED supports partial show.
                ";
              leaf name {
                tailf:info
                  "Option name";
                type string;
              }
              leaf value {
                tailf:info
                  "Option value";
                type string;
              }
            }
          }
        }
        case upgrade {
          description
            "An upgrade component is used to migrate data for packages
             where the YANG data model has changed and the automatic
             CDB upgrade is not sufficient. The upgrade component
             consists of either a Java class with a main method or a
             Python class with an upgrade method, that is expected to
             run one time only.";
          container upgrade {
            tailf:info
              "Upgrade component information";
            choice type {
              mandatory true;
              case java {
                leaf java-class-name {
                  tailf:info
                    "Name of the Java class that implements
                     the data migration";
                  type string;
                  description
                    "The name of the Java class that implements a main method
                     which will migrate data.";
                }
              }
              case python {
                leaf python-class-name {
                  tailf:info
                    "Name of the Python class that implements
                     the data migration";
                  type string;
                  description
                    "Name of the Python class that implements an upgrade
                     method which will migrate data.";
                }
              }
            }
          }
        }
        case callback {
          description
            "A data-provider can be used to implement NCS,
             services, external data providers, etc.";
          container callback {
            tailf:info
              "Callback component";
            leaf-list java-class-name {
              tailf:info
                "Java classes that implement the callback";
              type string;
              min-elements 1;
              description
                "The name of the Java class that is annotated with one of
                 the callback annotations 'ServiceCallback', 'ActionCallback',
                 'AuthCallback', 'DataCallback', 'DBCallback',
                 'SnmpInformResponseCallback', 'TransCallback',
                 'TransValidateCallback', or 'ValidateCallback'.";
            }
          }
        }
        case application {
          description
            "An application is a generic type with some
             Java code, and a Java class that is instantiated by NCS.";
          container application {
            tailf:info
              "Application component";
            choice type {
              mandatory true;
              case java {
                description
                  "Java application";
                leaf java-class-name {
                  tailf:info
                    "Java class that implements the application";
                  type string;
                  mandatory true;
                  description
                    "The name of the Java class that implements the
                     interface 'com.tailf.ncs.ApplicationComponent'.";
                }
              }
              case python {
                description
                  "Python application";
                leaf python-class-name {
                  tailf:info
                    "Python class that implements the application";
                  type string;
                  mandatory true;
                  description
                    "The name of the Python class that will be started by NCS.

                     An empty string here indicates a Python Library,
                     i.e., no code will be invoked by NCS. However, other
                     packages may depend on this package, thus getting the
                     PYTHONPATH setup to point to this package.";
                }
              }
            }
            leaf start-phase {
              tailf:info
                "NCS start phase where the package is instantiated";
              type enumeration {
                enum "phase1";
                enum "phase2";
              }
              default "phase2";
              description
                "The start phase where the package is instantiated.";
            }
          }
        }
      }
    }
  }

  grouping reload-params {
    leaf max-wait-time {
      tailf:info
        "Max time in seconds to wait for commit queue to become empty
         (if 'wait-for-commit-queue-empty' parameter is set) and
         transactions to close";
      type uint32 {
        range "0..4294967";
      }
      units "seconds";
      default "10";
      description
        "When a reload includes updated YANG code (.fxs files) or
         CLI specification files (.ccl files), NCS needs to run
         a data model upgrade procedure. This requires that all
         transactions are closed, in particular that users having
         CLI sessions in configure mode must exit to operational
         mode. The 'max-wait-time' is the maximum time to wait for
         this to complete.";
    }
    leaf timeout-action {
      tailf:info
        "Action taken when max-wait-time is reached";
      type enumeration {
        enum "fail" {
          tailf:info
            "Package reload is canceled";
        }
        enum "kill" {
          tailf:info
            "Open transactions are forcibly terminated";
        }
      }
      default "fail";
      description
        "If 'max-wait-time' is reached with transactions still open,
         the reload will be canceled if 'timeout-action' is 'fail'.
         If 'timeout-action' is 'kill', any remaining transactions
         will instead be forcibly terminated, and the reload will
         proceed.";
    }
    leaf force {
      tailf:info
        "Ignore warnings.";
      description
        "If this parameter is not given, then the action may abort if
         some dangerous operations need to be performed, such as removal of
         the whole namespace. By using this parameter the operator
         acknowledges this, and allows to proceed with the dangerous
         operations.";
      type empty;
    }
    leaf wait-commit-queue-empty {
      type empty;
      tailf:info
        "Enable waiting for commit queue to become empty";
      description
        "If the reload includes updated YANG code (.fxs files) or CLI
         specification files (.ccl files), it will block new transactions
         and wait for all the ongoing queue items to finish. The reload
         proceeds when the commit queue becomes empty. Otherwise, it will
         stop with an error.";
    }
  }

  augment "/ncs-internal:devices/ncs-internal:device/ncs-internal:config" {
    // NCS drop config false container packages
  }
  augment "/ncs-internal:devices/ncs-internal:device/ncs-internal:live-status" {
    container packages {
      tailf:ncs-device-type "netconf";
      tailf:display-when "not(../../ncs-internal:module) or ../../ncs-internal:module[ncs-internal:name='tailf-ncs'] or (../../ncs-internal:live-status-protocol[not(ncs-internal:capability)]) or (../../ncs-internal:live-status-protocol/ncs-internal:capability/ncs-internal:module[.='tailf-ncs'])";
      tailf:info
        "Installed packages";
      description
        "Lists all installed NCS packages.";
      // NCS drop tailf:callpoint
      list package {
        tailf:info
          "Show installed packages";
        key "name";
        // NCS expand uses statement

        typedef version {
          type live_ncs_package-version;
          description
            "The version is a sequence of numbers and words, separated by '.'
             or '-'.  When NCS compares a version string, it parses the string
             into the sequence of numbers and words, and compares each component
             individually.";
        }
        leaf name {
          tailf:info
            "A unique name, used to identify the package";
          type string;
          // NCS drop mandatory statement
          description
            "A unique name, used to identify the package.";
          // NCS drop tailf:cli-allow-range
        }
        leaf package-version {
          tailf:info
            "The version of the package";
          type version;
          // NCS drop mandatory statement
          description
            "The version of the package. An NCS customer that modifies a package
             is encouraged to add its own info to this string, e.g.
               1.2-acme-1
               1.2-acme-2";
        }
        leaf description {
          tailf:info
            "Free-form text describing the package";
          type string;
          description
            "Free-form text describing the package.";
        }
        leaf-list ncs-min-version {
          tailf:info
            "Minimum NCS versions, one per NCS major,  required by this package";
          type version;
          description
            "Minimum NCS versions, one per NCS major, required by this package.";
        }
        leaf-list ncs-max-version {
          tailf:info
            "Maximum NCS versions, one per NCS major,  required by this package";
          type version;
          description
            "Maximum NCS versions, one per NCS major, required by this package.";
        }
        container python-package {
          tailf:info
            "Python specific data.";
          presence "Python specific package data";
          leaf vm-name {
            type string;
            // NCS drop when statement
            description
              "A Python package will per default run in a seperate Python VM.
               This Python VM will get a symbolic name (for reference from
               within NCS) which per default is the package 'name'.

               However, by setting 'vm-name', its value will be used as as
               the symbolic name for the Python VM started. This will
               cause packages with the same 'vm-name' to run in the same
               Python VM.";
          }
          leaf callpoint-model {
            type enumeration {
              enum "threading";
              enum "multiprocessing";
            }
            // NCS drop default statement
            description
              "A Python package will per default run all Services, Nano Services
               and Actions in the same OS process. If this is set to multiprocessing
               a separate worker process will be created for each Service,
               Nano Service and Action.

               In parallel workloads the multiprocessing callpoint model
               can improve the performance of the services";
          }
        }
        leaf directory {
          tailf:info
            "The path to the directory of the package";
          type string;
          description
            "The path to the directory of the package.";
        }
        leaf-list templates {
          tailf:info
            "The templates defined by this package";
          type string;
          description
            "The templates defined by this package.";
        }
        leaf template-loading-mode {
          type enumeration {
            enum "strict";
            enum "relaxed";
          }
          description
            "This leaf indicates whether the templates in this package are
             interpreted in strict mode or relaxed mode. It is unset if the package
             has no templates.

             Strict mode means we report all schema-related errors in templates
             that can be identified at load time (such as unknown namespace, schema
             ambiguity or unknown ned-id). Strict mode is applid when there are no
             supported-ned-ids declared or when all of the supported-ned-ids are
             loaded.

             If the package declares supported-ned-ids, but some of them are not
             recognized, then we assume relaxed mode as we will not be able to
             identify some of the schema-related errors, for example we might need
             to skip over tags in unknown namespaces because they might belong
             to the missing ned-ids that the package supports, but that are
             currently not loaded in the runtime system.

             It is important that the package developer tests the package with
             all the supported-ned-ids loaded, i.e. in strict mode, as it helps
             catch errors that may be ignored in relaxed mode.";
        }
        leaf-list supported-ned-id {
          tailf:info
            "The list of ned-ids supported by this package";
          type union {
            // NCS patched to string, due to LSA partial NED
            type string;
            type string;
          }
          description
            "Templates defined by this package will be applied in the scope of
             this list of ned-ids. Trying to apply a template defined by this
             package to a device with a different ned-id will result at runtime
             error. If no supported-ned-id is defined, then no such restrictions
             are placed on this package's templates, however it may lead to a
             situation where loading an additional NED can prevent the package
             defining the template from loading by making a template ambiguous.

             This parameter has no effect for packages that define no templates.";
        }
        leaf-list supported-ned-id-match {
          tailf:info
            "List of regexes for ned-ids supported by this package";
          type string;
          description
            "This list is used to populate 'supported-ned-id' with the help
             of regular expressions. Ned-ids in the system that match at least
             one of the regular expressions in this list are added to the
             'supported-ned-id' list.";
        }
        list required-package {
          tailf:info
            "A list of packages required by this package";
          key "name";
          description
            "A list of packages required by this package.  NCS will not
             load any package with missing dependencies.";
          leaf name {
            tailf:info
              "Required package name";
            type string;
          }
          leaf min-version {
            tailf:info
              "Required package minimum version";
            type version;
            description
              "Minimum version required by this package.";
          }
          leaf max-version {
            tailf:info
              "Required package maximum version";
            type version;
            description
              "Maximum version required by this package.";
          }
        }
        list component {
          tailf:info
            "Package components";
          key "name";
          leaf name {
            tailf:info
              "Component name";
            type string;
            description
              "A unique name, used to identify the component within
               the package.";
          }
          leaf description {
            tailf:info
              "Free-form text describing the component";
            type string;
            description
              "Free-form text describing the component.";
          }
          leaf entitlement-tag {
            tailf:info
              "Entitlement tag for Smart Licensing.";
            type string;
            description
              "Identifies the component for Smart Licensing.";
          }
          choice type {
            // NCS drop mandatory statement
            case ned {
              description
                "A NED package typically contains the YANG models for
                 the device, and Java classes derived from these modules.
                 The Java classes are delivered as 'shared' jar files, which
                 makes them available for Java services and other Java code
                 to use.";
              container ned {
                tailf:info
                  "NED component";
                choice ned-type {
                  // NCS drop mandatory statement
                  container netconf {
                    tailf:info
                      "NETCONF NED";
                    description
                      "A NETCONF NED typically consists of the YANG modules
                       for the device, and Java classes derived from these
                       modules.";
                    leaf ned-id {
                      tailf:info
                        "The NETCONF NED identity";
                      // NCS patched to string, due to LSA partial NED
                      type string;
                      // NCS drop mandatory statement
                      description
                        "The identity that identifies the NETCONF NED. If
                         let empty it is just a plain NETCONF NED.";
                    }
                  }
                  container snmp {
                    tailf:info
                      "SNMP NED";
                    description
                      "An SNMP NED typically consists of the MIB modules
                       for the device, YANG modules derived from the MIBs, and
                       Java classes derived from these models.";
                    leaf ned-id {
                      tailf:info
                        "The SNMP NED identity";
                      // NCS patched to string, due to LSA partial NED
                      type string;
                      description
                        "The identity that identifies the SNMP NED.";
                    }
                  }
                  container cli {
                    tailf:info
                      "CLI NED";
                    description
                      "A CLI NED typically consists of YANG models for the
                       device, Java classes derived from these modules, and
                       a Java class responsible for the communication with the
                       device.";
                    leaf ned-id {
                      tailf:info
                        "The CLI NED identity";
                      // NCS patched to string, due to LSA partial NED
                      type string;
                      // NCS drop mandatory statement
                      description
                        "The identity that identifies the CLI NED.  All
                         devices of type 'cli' that are configured with
                         this 'ned-id' are handled by this compontent's 'NedCli'
                         Java class.";
                    }
                    leaf java-class-name {
                      tailf:info
                        "Name of the Java class that implements the NED";
                      type string;
                      // NCS drop mandatory statement
                      description
                        "The name of the Java class that implements the
                         interface 'NedCli'.";
                    }
                  }
                  container generic {
                    tailf:info
                      "Generic NED";
                    description
                      "A Generic NED typically consists of YANG models for the
                       device, Java classes derived from these modules, and
                       a Java class responsible for the communication with the
                       device.";
                    leaf ned-id {
                      tailf:info
                        "The Generic NED identity";
                      // NCS patched to string, due to LSA partial NED
                      type string;
                      // NCS drop mandatory statement
                      description
                        "The identity that identifies the Generic NED.  All
                         devices of type 'generic' that are configured with
                         this 'ned-id' are handled by this component's 'NedGeneric'
                         Java class.";
                    }
                    leaf java-class-name {
                      tailf:info
                        "Name of the Java class that implements the NED";
                      type string;
                      // NCS drop mandatory statement
                      description
                        "The name of the Java class that implements the
                         interface 'NedGeneric'.";
                    }
                  }
                }
                container device {
                  tailf:info
                    "NED device type information";
                  leaf vendor {
                    tailf:info
                      "Vendor name";
                    type string;
                    // NCS drop mandatory statement
                    description
                      "Free-form string, used for documentation purposes.";
                  }
                  leaf product-family {
                    tailf:info
                      "Product family";
                    type string;
                    description
                      "The product-specific family of products supported by this
                       NED.

                       In some cases, this could be as generic as 'ios', if the
                       NED works with any ios release.  In other cases it could
                       be as specific as 'ios-11.4' if it works only with ios
                       release 11.4.  And in some cases, it would be some middle
                       ground, e.g., 'ios-11' or 'ios-11+'.";
                  }
                }
                list option {
                  tailf:info
                    "NED specific options";
                  key "name";
                  description
                    "A list of options to configure the behavior of this NED.
                     Available options are:

                      ordered-diff (for generic NEDs),
                         Order the operations sent the NED such that
                         dependencies are taken into account, ie if a
                         list element is deleted and there are leafref
                         references to the instance, order the leafref
                         in front of the delete of the instance.

                      show-tag (for CLI NEDs)
                         If set the NED will only ask for one top-tag in
                         the show() callback instead of invoking the show()
                         callback once for each top-tag. Many NEDs return
                         the entire configuration in one go and are only
                         interested in one show() invocation. The common
                         workaround is to only return when the show() command
                         is invoked with a specific top-tag, and return the
                         empty string for the rest. With this option set
                         there will only be one show() invocation.

                      allow-abbrevs (for CLI NEDs)
                         When set abbreviated commands are allowed to be
                         sent in the response to the show() callback. Devices
                         typically do not generate abbreviated commands and
                         setting the above option may introduce ambiguity in
                         the parsing.

                      show-partial
                        Set if the NED supports partial show.
                    ";
                  leaf name {
                    tailf:info
                      "Option name";
                    type string;
                  }
                  leaf value {
                    tailf:info
                      "Option value";
                    type string;
                  }
                }
              }
            }
            case upgrade {
              description
                "An upgrade component is used to migrate data for packages
                 where the YANG data model has changed and the automatic
                 CDB upgrade is not sufficient. The upgrade component
                 consists of either a Java class with a main method or a
                 Python class with an upgrade method, that is expected to
                 run one time only.";
              container upgrade {
                tailf:info
                  "Upgrade component information";
                choice type {
                  // NCS drop mandatory statement
                  case java {
                    leaf java-class-name {
                      tailf:info
                        "Name of the Java class that implements
                         the data migration";
                      type string;
                      description
                        "The name of the Java class that implements a main method
                         which will migrate data.";
                    }
                  }
                  case python {
                    leaf python-class-name {
                      tailf:info
                        "Name of the Python class that implements
                         the data migration";
                      type string;
                      description
                        "Name of the Python class that implements an upgrade
                         method which will migrate data.";
                    }
                  }
                }
              }
            }
            case callback {
              description
                "A data-provider can be used to implement NCS,
                 services, external data providers, etc.";
              container callback {
                tailf:info
                  "Callback component";
                leaf-list java-class-name {
                  tailf:info
                    "Java classes that implement the callback";
                  type string;
                  // NCS drop min-elements statement
                  description
                    "The name of the Java class that is annotated with one of
                     the callback annotations 'ServiceCallback', 'ActionCallback',
                     'AuthCallback', 'DataCallback', 'DBCallback',
                     'SnmpInformResponseCallback', 'TransCallback',
                     'TransValidateCallback', or 'ValidateCallback'.";
                }
              }
            }
            case application {
              description
                "An application is a generic type with some
                 Java code, and a Java class that is instantiated by NCS.";
              container application {
                tailf:info
                  "Application component";
                choice type {
                  // NCS drop mandatory statement
                  case java {
                    description
                      "Java application";
                    leaf java-class-name {
                      tailf:info
                        "Java class that implements the application";
                      type string;
                      // NCS drop mandatory statement
                      description
                        "The name of the Java class that implements the
                         interface 'com.tailf.ncs.ApplicationComponent'.";
                    }
                  }
                  case python {
                    description
                      "Python application";
                    leaf python-class-name {
                      tailf:info
                        "Python class that implements the application";
                      type string;
                      // NCS drop mandatory statement
                      description
                        "The name of the Python class that will be started by NCS.

                         An empty string here indicates a Python Library,
                         i.e., no code will be invoked by NCS. However, other
                         packages may depend on this package, thus getting the
                         PYTHONPATH setup to point to this package.";
                    }
                  }
                }
                leaf start-phase {
                  tailf:info
                    "NCS start phase where the package is instantiated";
                  type enumeration {
                    enum "phase1";
                    enum "phase2";
                  }
                  // NCS drop default statement
                  description
                    "The start phase where the package is instantiated.";
                }
              }
            }
          }
        }
        tailf:action redeploy {
          tailf:actionpoint ncsproxy {
            tailf:internal;
          }
          tailf:info
            "Redeploy a single package's code";
          // NCS drop tailf:actionpoint
          description
            "Redeploy a single package. This means that Java code contained
             in the private-jar directory, templates belonging to this package,
             Python code and webui customizations will be reloaded if they are
             found to be different from those currently loaded in NCS. Note
             that if YANG modules, Java code in shared-jar directory or
             package-meta-data.xml has been changed, it is necessary to use
             the /packages/reload action.";
          input;
          output {
            leaf result {
              description
                "This leaf indicates whether the package's oper-status is 'up'
                 after the redeploy operation.";
              type boolean;
            }
          }
        }
        container build-info {
          description
            "Detailed build/revision info for the package";
          leaf date {
            type string;
          }
          leaf file {
            type string;
          }
          leaf arch {
            type string;
          }
          leaf java {
            description
              "Details about the Java version used to build the package";
            type string;
          }
          leaf python {
            description
              "Details about the Python version used to build the package";
            type string;
          }
          leaf erlang {
            description
              "Details about the Erlang version used to build the package";
            type string;
          }
          container package {
            description
              "Revision info for the package";
            leaf name {
              type string;
            }
            leaf version {
              type string;
            }
            leaf ref {
              type string;
            }
            leaf sha1 {
              type string;
            }
          }
          container ncs {
            description
              "Revision info for the NCS used to build the package";
            leaf version {
              type string;
            }
            leaf sha1 {
              type string;
            }
          }
          container dev-support {
            description
              "Revision info for the support libs
               used to build the package";
            leaf version {
              type string;
            }
            leaf branch {
              type string;
            }
            leaf sha1 {
              type string;
            }
          }
        }
        container oper-status {
          tailf:info
            "The operational status of the package";
          choice status {
            // NCS drop mandatory statement
            leaf up {
              type empty;
              description
                "The package has all its dependencies fulfilled, and
                 has been loaded by NCS.";
            }
            leaf program-code-error {
              type empty;
              description
                "The package has a program code related error.
                 Any error message will be appended to 'error-info'.";
            }
            leaf java-uninitialized {
              type empty;
              description
                "The package's Java classes have not yet been loaded and
                 initialized.";
            }
            leaf python-uninitialized {
              type empty;
              description
                "The package's Python classes have not yet been loaded and
                 initialized.";
            }
            leaf bad-ncs-version {
              type empty;
              description
                "The package requires a later NCS version than what is
                 currently running.";
            }
            container missing-dependency {
              description
                "The package requires another package, which is not
                 installed, or is installed with a too small version.";
              leaf package-name {
                type string;
                // NCS drop mandatory statement
                description
                  "The name of the required package.";
              }
              leaf package-version {
                type string;
                description
                  "The version of the required package.";
              }
            }
            leaf circular-dependency {
              type empty;
              description
                "A circular dependency loop involving this package was
                 detected.";
            }
            leaf package-meta-data-error {
              type empty;
              description
                "Could not parse the package meta data.";
            }
            leaf file-load-error {
              type empty;
              description
                "Failed to load some file in the package.";
            }
          }
          leaf-list error-info {
            type string;
            description
              "Contains additional information, if available, when the
               status is not equal to 'up'.";
          }
          leaf-list warnings {
            type string;
            description
              "List of package warnings.";
          }
        }
      }
      tailf:action reload {
        tailf:actionpoint ncsproxy {
          tailf:internal;
        }
        tailf:info
          "Reload all packages";
        // NCS drop tailf:actionpoint
        tailf:cli-operational-mode;
        description
          "Reloads all packages. This means that all parts of all packages
           will be copied to NCS' private directory, reloaded, and restarted.";
        input {
          uses live_ncs_reload-params;
        }
        output {
          list reload-result {
            key "package";
            leaf package {
              type leafref {
                path "/ncs-internal:devices/ncs-internal:device/ncs-internal:live-status/packages/package/name" {
                  tailf:xpath-root 3;
                }
              }
            }
            leaf result {
              type boolean;
              description
                "true if package was successfully loaded";
            }
            leaf info {
              type string;
              description
                "If present, contains additional information about the result.";
            }
          }
        }
      }
      container ha {
        // NCS drop when statement
        tailf:action sync {
          tailf:actionpoint ncsproxy {
            tailf:internal;
          }
          tailf:info
            "Sync packages in a HA cluster";
          description
            "The action syncs the packages from the primary to the secondary
             nodes. After the sync is successfully completed, and if 'and-reload'
             input parameter is specified, it reloads the packages on both the
             primary and secondary nodes. The action does not perform the sync
             and the reload on the node with none role.

             The sync action finds packages from the load paths and transfers
             them as tar archives to the secondary nodes, regardless if the
             primary node packages are in directories of files or tar archives
             with the directory of files. Therefore, it is required that both
             primary and secondary nodes have identical load path configuration
             in /ncs-config/load-path. If there is an existing package on the
             secondary node, it will replace it with the one on the primary. If a
             package is deleted on the primary node, it will also delete the
             package on the secondary nodes.";
          // NCS drop tailf:actionpoint
          tailf:cli-operational-mode;
          input {
            container and-reload {
              tailf:info
                "Reload the packages after distribution is successfully
                 completed";
              description
                "The reload is performed on all the HA nodes. Before the reload,
                 the node will be set to read-only mode. After the upgrade is
                 successfully completed, the node will be set back to its previous
                 mode. If an error occurs during the upgrade, the node will be
                 left in read-only mode for further manual investigation.";
              presence "reload packages";
              uses live_ncs_reload-params;
            }
          }
          output {
            list sync-result {
              key "node-id";
              leaf node-id {
                type string;
                description
                  "HA node ID";
              }
              leaf result {
                type boolean;
                description
                  "true if the operation was successful";
              }
              leaf info {
                type string;
                description
                  "If present, contains additional information about the
                   result.";
              }
            }
          }
        }
      }
    }
  }
  augment "/ncs-internal:devices/ncs-internal:template/ncs-internal:ned-id/ncs-internal:config" {
    // NCS drop config false container packages
  }
  augment "/ncs-internal:compliance/ncs-internal:template/ncs-internal:ned-id/ncs-internal:config" {
    // NCS drop config false container packages
  }
}
