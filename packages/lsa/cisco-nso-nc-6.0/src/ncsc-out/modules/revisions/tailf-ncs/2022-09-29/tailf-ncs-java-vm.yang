submodule tailf-ncs-java-vm {
  // Generated by yanger -t ncs
  tailf:mount-id "cisco-nso-nc-6.0:cisco-nso-nc-6.0";

  yang-version 1.1;
  belongs-to tailf-ncs {
    prefix ncs;
  }

  import ietf-inet-types {
    prefix inet;
  }
  import tailf-common {
    prefix tailf;
  }
  import tailf-ncs-internal-mount {
    prefix ncs-internal;
  }

  organization
    "Tail-f Systems";
  description
    "This submodule contains a collection of YANG definitions for
     configuring and monitoring the Java Virtual Machine in NCS.

     Copyright 2012-2022 Cisco Systems, Inc.
     All rights reserved.
     Permission is hereby granted to redistribute this file without
     modification.";

  revision 2022-04-12 {
    description
      "Released as part of NCS-5.8.

       Non-backwards-compatible changes have been introduced.

       Removed obsoleted /java-vm/service-transaction-timeout leaf.";
  }
  revision 2021-09-02 {
    description
      "Released as part of NCS-5.6.

       Obsoleted /java-vm/service-transaction-timeout.";
  }
  revision 2019-11-28 {
    description
      "Released as part of NCS-5.3.

       Added a code-name to the log enum.";
  }
  revision 2019-04-09 {
    description
      "Released as part of NCS-5.1.

       Removed /java-vm/start-command, /java-vm/auto-start,
       /java-vm/auto-restart and /java-vm/run-in-terminal.

       Added tailf:hidden to /java-vm/stdout-capture,
       /java-vm/connect-time, /java-vm/initialization-time,
       /java-vm/synchronization-timeout-action,
       /java-vm/exception-error-message, /java-vm/jmx,
       /java-vm/stop, /java-vm/start and /java-vm/restart.";
  }
  revision 2017-07-09 {
    description
      "Released as part of NCS-4.4.2.1.

       Updated description of /java-vm/start-command and
       /java-vm/run-in-terminal/terminal-command.";
  }
  revision 2017-03-16 {
    description
      "Released as part of NCS-4.4.

       Added range to all config leafs specifying time.";
  }
  revision 2013-04-24 {
    description
      "Released as part of NCS-2.2.1.

       Added /java-vm/exception-error-message.";
  }
  revision 2012-11-13 {
    description
      "Released as part of NCS-2.1.

       Removed /java-vm/java-thread-pool.";
  }
  revision 2012-08-30 {
    description
      "Released as part of NCS-2.0.";
  }

  typedef ncs_compliance_template_error-verbosity-type {
    type string;
    description
      "Levels of verbosity for Exception error messages in DP";
  }

  typedef ncs_compliance_template_log-level-type {
    type string;
    description
      "Levels of logging for Java packages in log4j.";
  }

  typedef ncs_template_error-verbosity-type {
    type string;
    description
      "Levels of verbosity for Exception error messages in DP";
  }

  typedef ncs_template_log-level-type {
    type string;
    description
      "Levels of logging for Java packages in log4j.";
  }

  typedef ncs_rpc_notif_error-verbosity-type {
    type enumeration {
      enum "standard" {
        value 0;
        tailf:code-name "error_standard";
      }
      enum "verbose" {
        value 1;
        tailf:code-name "error_verbose";
      }
      enum "trace" {
        tailf:code-name "error_trace";
        value 2;
      }
    }
    description
      "Levels of verbosity for Exception error messages in DP";
  }

  typedef ncs_rpc_notif_log-level-type {
    type enumeration {
      enum "level-all" {
        value 1;
      }
      enum "level-debug" {
        value 2;
      }
      enum "level-error" {
        value 3;
      }
      enum "level-fatal" {
        value 4;
      }
      enum "level-info" {
        value 5;
      }
      enum "level-off" {
        value 6;
      }
      enum "level-trace" {
        value 7;
      }
      enum "level-warn" {
        value 8;
      }
    }
    description
      "Levels of logging for Java packages in log4j.";
  }

  typedef live_ncs_error-verbosity-type {
    type enumeration {
      enum "standard" {
        value 0;
        tailf:code-name "error_standard";
      }
      enum "verbose" {
        value 1;
        tailf:code-name "error_verbose";
      }
      enum "trace" {
        tailf:code-name "error_trace";
        value 2;
      }
    }
    description
      "Levels of verbosity for Exception error messages in DP";
  }

  typedef live_ncs_log-level-type {
    type enumeration {
      enum "level-all" {
        value 1;
      }
      enum "level-debug" {
        value 2;
      }
      enum "level-error" {
        value 3;
      }
      enum "level-fatal" {
        value 4;
      }
      enum "level-info" {
        value 5;
      }
      enum "level-off" {
        value 6;
      }
      enum "level-trace" {
        value 7;
      }
      enum "level-warn" {
        value 8;
      }
    }
    description
      "Levels of logging for Java packages in log4j.";
  }

  typedef error-verbosity-type {
    type enumeration {
      enum "standard" {
        value 0;
        tailf:code-name "error_standard";
      }
      enum "verbose" {
        value 1;
        tailf:code-name "error_verbose";
      }
      enum "trace" {
        tailf:code-name "error_trace";
        value 2;
      }
    }
    description
      "Levels of verbosity for Exception error messages in DP";
  }

  typedef log-level-type {
    type enumeration {
      enum "level-all" {
        value 1;
      }
      enum "level-debug" {
        value 2;
      }
      enum "level-error" {
        value 3;
      }
      enum "level-fatal" {
        value 4;
      }
      enum "level-info" {
        value 5;
      }
      enum "level-off" {
        value 6;
      }
      enum "level-trace" {
        value 7;
      }
      enum "level-warn" {
        value 8;
      }
    }
    description
      "Levels of logging for Java packages in log4j.";
  }

  augment "/ncs-internal:devices/ncs-internal:device/ncs-internal:config" {
    container java-vm {
      tailf:ncs-device-type "netconf";
      tailf:display-when "not(../../ncs-internal:module) or ../../ncs-internal:module[ncs-internal:name='tailf-ncs']";
      tailf:info
        "Control of the NCS Java VM";
      description
        "Configuration parameters to control various properties of the
         Java application code, e.g., logging, and statistics data about
         the Java application code.";
      container stdout-capture {
        tailf:hidden "debug";
        tailf:info
          "Capture stdout and stderr";
        description
          "Capture stdout and stderr from the Java VM.

           Only applicable if auto-start is 'true'.";
        leaf enabled {
          tailf:info
            "Enable stdout and stderr capture";
          type boolean;
          default "true";
          description
            "NOTE: If a value is set for
             /ncs-config/java-vm/stdout-capture/enabled
             in ncs.conf, the value set here is ignored.";
        }
        leaf file {
          tailf:info
            "Write Java VM output to file";
          type string;
          default "./ncs-java-vm.log";
          description
            "Write Java VM output to filename.

             NOTE: If a value is set for
             /ncs-config/java-vm/stdout-capture/file
             in ncs.conf, the value set here is ignored.";
        }
        leaf stdout {
          tailf:info
            "Write output to stdout";
          type empty;
          description
            "If present write output to stdout, useful together
             with the --foreground flag to ncs.";
        }
      }
      leaf connect-time {
        tailf:hidden "debug";
        tailf:info
          "The time NCS waits for the Java VM to connect to NCS";
        type uint32 {
          range "1..4294967";
        }
        units "seconds";
        default "60";
        description
          "The time NCS waits for the Java VM to connect to NCS
           during a synchronous startup of NCS.

           If the timer expires the action defined in
           'synchronization-timeout-action' is taken.";
      }
      leaf initialization-time {
        tailf:hidden "debug";
        tailf:info
          "Timeout for each NCS package component to initialize";
        type uint32 {
          range "1..4294967";
        }
        units "seconds";
        default "60";
        description
          "The time NCS waits for each NCS package component to
           initialize itself.

           If the timer expires the action defined in
           'synchronization-timeout-action' is taken.";
      }
      leaf synchronization-timeout-action {
        tailf:hidden "debug";
        tailf:info
          "If the synchronous startup fails";
        type enumeration {
          enum "log" {
            tailf:info
              "Log this error condition and continue";
            tailf:code-name "log_timeout";
            description
              "Log this error condition and continue.";
          }
          enum "log-stop" {
            tailf:info
              "Log this error condition and try to stop the Java VM";
            description
              "Log this error condition and try to stop the Java VM.

               If auto-start is 'false', this action is identical to
               'log'.";
          }
          enum "exit" {
            tailf:info
              "Terminate NCS fatally";
            description
              "Terminate NCS fatally.";
          }
        }
        default "log-stop";
        description
          "The action NCS takes if any of the timers 'connect-time' or
           'initialization-time' expires.";
      }
      container exception-error-message {
        tailf:hidden "debug";
        tailf:info
          "Configure Java Exception error message verbosity";
        leaf verbosity {
          tailf:info
            "Verbosity level for exception error messages";
          type error-verbosity-type;
          description
            "Verbosity level value for error messages in the Java VM.";
        }
      }
      container java-logging {
        tailf:info
          "Configure Java Logging";
        list logger {
          tailf:info
            "List of loggers";
          key "logger-name";
          description
            "Each entry in this list holds one representation of a logger with
             a specific level defined by log-level-type. The logger-name
             is the name of a Java package.  logger-name can thus be for
             example com.tailf.maapi, or com.tailf etc.";
          leaf logger-name {
            tailf:info
              "The name of the Java package";
            type string;
            mandatory true;
            description
              "The name of the Java package for which this logger
               entry applies.";
          }
          leaf level {
            tailf:info
              "Log-level for this logger";
            type log-level-type;
            mandatory true;
            description
              "Corresponding log-level for a specific logger.";
          }
        }
      }
      container jmx {
        tailf:hidden "debug";
        tailf:info
          "Java Management Extensions settings";
        presence "Start a Java Management Extensions (JMX) Agent in the Java VM";
        leaf jndi-address {
          tailf:info
            "The hostname or ip for the RMI registry";
          type inet:ip-address;
          default "0.0.0.0";
          description
            "The hostname or ip for the RMI registry";
        }
        leaf jndi-port {
          tailf:info
            "The port for the RMI registry";
          type inet:port-number;
          default "4444";
          description
            "The port for the RMI registry";
        }
        leaf jmx-address {
          tailf:info
            "The hostname or ip for the JMX RMI server";
          type inet:ip-address;
          default "0.0.0.0";
          description
            "The hostname or ip for the JMX RMI server";
        }
        leaf jmx-port {
          tailf:info
            "The port for the JMX RMI server";
          type inet:port-number;
          default "4445";
          description
            "The port for the JMX RMI server";
        }
      }
      // NCS drop config false leaf 'start-status'
      // NCS drop config false leaf status
      tailf:action stop {
        tailf:actionpoint ncsproxy {
          tailf:internal;
        }
        tailf:hidden "debug";
        tailf:info
          "Stop the Java VM";
        description
          "Stop the NCS Java VM.

           Only applicable if auto-start is 'true'.";
        // NCS drop tailf:actionpoint
        output {
          leaf result {
            type string;
          }
        }
      }
      tailf:action start {
        tailf:actionpoint ncsproxy {
          tailf:internal;
        }
        tailf:hidden "debug";
        tailf:info
          "Stop the Java VM";
        description
          "Start the Java VM.

           Only applicable if auto-start is 'true'.";
        // NCS drop tailf:actionpoint
        output {
          leaf result {
            type string;
          }
        }
      }
      tailf:action restart {
        tailf:actionpoint ncsproxy {
          tailf:internal;
        }
        tailf:hidden "debug";
        tailf:info
          "Restart the Java VM";
        description
          "Restart the Java VM.

           Only applicable if auto-start is 'true'.";
        // NCS drop tailf:actionpoint
        output {
          leaf result {
            type string;
          }
        }
      }
    }
  }
  augment "/ncs-internal:devices/ncs-internal:device/ncs-internal:live-status" {
    container java-vm {
      tailf:ncs-device-type "netconf";
      tailf:display-when "not(../../ncs-internal:module) or ../../ncs-internal:module[ncs-internal:name='tailf-ncs'] or (../../ncs-internal:live-status-protocol[not(ncs-internal:capability)]) or (../../ncs-internal:live-status-protocol/ncs-internal:capability/ncs-internal:module[.='tailf-ncs'])";
      tailf:info
        "Control of the NCS Java VM";
      description
        "Configuration parameters to control various properties of the
         Java application code, e.g., logging, and statistics data about
         the Java application code.";
      container stdout-capture {
        tailf:hidden "debug";
        tailf:info
          "Capture stdout and stderr";
        description
          "Capture stdout and stderr from the Java VM.

           Only applicable if auto-start is 'true'.";
        leaf enabled {
          tailf:info
            "Enable stdout and stderr capture";
          type boolean;
          // NCS drop default statement
          description
            "NOTE: If a value is set for
             /ncs-config/java-vm/stdout-capture/enabled
             in ncs.conf, the value set here is ignored.";
        }
        leaf file {
          tailf:info
            "Write Java VM output to file";
          type string;
          // NCS drop default statement
          description
            "Write Java VM output to filename.

             NOTE: If a value is set for
             /ncs-config/java-vm/stdout-capture/file
             in ncs.conf, the value set here is ignored.";
        }
        leaf stdout {
          tailf:info
            "Write output to stdout";
          type empty;
          description
            "If present write output to stdout, useful together
             with the --foreground flag to ncs.";
        }
      }
      leaf connect-time {
        tailf:hidden "debug";
        tailf:info
          "The time NCS waits for the Java VM to connect to NCS";
        type uint32 {
          range "1..4294967";
        }
        units "seconds";
        // NCS drop default statement
        description
          "The time NCS waits for the Java VM to connect to NCS
           during a synchronous startup of NCS.

           If the timer expires the action defined in
           'synchronization-timeout-action' is taken.";
      }
      leaf initialization-time {
        tailf:hidden "debug";
        tailf:info
          "Timeout for each NCS package component to initialize";
        type uint32 {
          range "1..4294967";
        }
        units "seconds";
        // NCS drop default statement
        description
          "The time NCS waits for each NCS package component to
           initialize itself.

           If the timer expires the action defined in
           'synchronization-timeout-action' is taken.";
      }
      leaf synchronization-timeout-action {
        tailf:hidden "debug";
        tailf:info
          "If the synchronous startup fails";
        type enumeration {
          enum "log" {
            tailf:info
              "Log this error condition and continue";
            tailf:code-name "log_timeout";
            description
              "Log this error condition and continue.";
          }
          enum "log-stop" {
            tailf:info
              "Log this error condition and try to stop the Java VM";
            description
              "Log this error condition and try to stop the Java VM.

               If auto-start is 'false', this action is identical to
               'log'.";
          }
          enum "exit" {
            tailf:info
              "Terminate NCS fatally";
            description
              "Terminate NCS fatally.";
          }
        }
        // NCS drop default statement
        description
          "The action NCS takes if any of the timers 'connect-time' or
           'initialization-time' expires.";
      }
      container exception-error-message {
        tailf:hidden "debug";
        tailf:info
          "Configure Java Exception error message verbosity";
        leaf verbosity {
          tailf:info
            "Verbosity level for exception error messages";
          type live_ncs_error-verbosity-type;
          description
            "Verbosity level value for error messages in the Java VM.";
        }
      }
      container java-logging {
        tailf:info
          "Configure Java Logging";
        list logger {
          tailf:info
            "List of loggers";
          key "logger-name";
          description
            "Each entry in this list holds one representation of a logger with
             a specific level defined by log-level-type. The logger-name
             is the name of a Java package.  logger-name can thus be for
             example com.tailf.maapi, or com.tailf etc.";
          leaf logger-name {
            tailf:info
              "The name of the Java package";
            type string;
            // NCS drop mandatory statement
            description
              "The name of the Java package for which this logger
               entry applies.";
          }
          leaf level {
            tailf:info
              "Log-level for this logger";
            type live_ncs_log-level-type;
            // NCS drop mandatory statement
            description
              "Corresponding log-level for a specific logger.";
          }
        }
      }
      container jmx {
        tailf:hidden "debug";
        tailf:info
          "Java Management Extensions settings";
        presence "Start a Java Management Extensions (JMX) Agent in the Java VM";
        leaf jndi-address {
          tailf:info
            "The hostname or ip for the RMI registry";
          type inet:ip-address;
          // NCS drop default statement
          description
            "The hostname or ip for the RMI registry";
        }
        leaf jndi-port {
          tailf:info
            "The port for the RMI registry";
          type inet:port-number;
          // NCS drop default statement
          description
            "The port for the RMI registry";
        }
        leaf jmx-address {
          tailf:info
            "The hostname or ip for the JMX RMI server";
          type inet:ip-address;
          // NCS drop default statement
          description
            "The hostname or ip for the JMX RMI server";
        }
        leaf jmx-port {
          tailf:info
            "The port for the JMX RMI server";
          type inet:port-number;
          // NCS drop default statement
          description
            "The port for the JMX RMI server";
        }
      }
      leaf start-status {
        tailf:info
          "";
        type enumeration {
          enum "auto-start-not-enabled" {
            description
              "Auto start is not enabled.";
          }
          enum "stopped" {
            description
              "The Java VM has been stopped or is not yet started.";
          }
          enum "started" {
            description
              "The Java VM has been started.  See the leaf 'status' to check
               the status of the Java application code.";
            tailf:code-name "jvm_started";
          }
          enum "failed" {
            description
              "The Java VM has terminated.  If 'auto-restart'
               is enabled, the Java VM restart has been
               disabled due to too many frequent restarts.";
          }
        }
        description
          "The status of the start of the Java VM.  If auto-start is 'false',
           this leaf is 'auto-start-not-enabled'.";
        // NCS drop tailf:callpoint
      }
      leaf status {
        tailf:info
          "Java application status";
        type enumeration {
          enum "not-connected" {
            description
              "The Java application code is not connected to NCS.";
          }
          enum "initializing" {
            description
              "The Java application code is connected to NCS, but not
               yet initialized.";
            tailf:code-name "jvm_initializing";
          }
          enum "running" {
            description
              "The Java application code is connected and initialized.";
            tailf:code-name "jvm_running";
          }
          enum "timeout" {
            description
              "The Java application connected to NCS, but failed to initialize
               within the stipulated timeout 'initialization-time'.";
            tailf:code-name "jvm_timeout";
          }
        }
        description
          "This leaf describes the status of the Java application code
           in NCS.";
        // NCS drop tailf:callpoint
      }
      tailf:action stop {
        tailf:actionpoint ncsproxy {
          tailf:internal;
        }
        tailf:hidden "debug";
        tailf:info
          "Stop the Java VM";
        description
          "Stop the NCS Java VM.

           Only applicable if auto-start is 'true'.";
        // NCS drop tailf:actionpoint
        output {
          leaf result {
            type string;
          }
        }
      }
      tailf:action start {
        tailf:actionpoint ncsproxy {
          tailf:internal;
        }
        tailf:hidden "debug";
        tailf:info
          "Stop the Java VM";
        description
          "Start the Java VM.

           Only applicable if auto-start is 'true'.";
        // NCS drop tailf:actionpoint
        output {
          leaf result {
            type string;
          }
        }
      }
      tailf:action restart {
        tailf:actionpoint ncsproxy {
          tailf:internal;
        }
        tailf:hidden "debug";
        tailf:info
          "Restart the Java VM";
        description
          "Restart the Java VM.

           Only applicable if auto-start is 'true'.";
        // NCS drop tailf:actionpoint
        output {
          leaf result {
            type string;
          }
        }
      }
    }
  }
  augment "/ncs-internal:devices/ncs-internal:template/ncs-internal:ned-id/ncs-internal:config" {
    container java-vm {
      description
        "Configuration parameters to control various properties of the
         Java application code, e.g., logging, and statistics data about
         the Java application code.";
      container stdout-capture {
        tailf:hidden "debug";
        description
          "Capture stdout and stderr from the Java VM.

           Only applicable if auto-start is 'true'.";
        leaf enabled {
          type string;
          // NCS drop default statement
          description
            "NOTE: If a value is set for
             /ncs-config/java-vm/stdout-capture/enabled
             in ncs.conf, the value set here is ignored.";
        }
        leaf file {
          type string;
          // NCS drop default statement
          description
            "Write Java VM output to filename.

             NOTE: If a value is set for
             /ncs-config/java-vm/stdout-capture/file
             in ncs.conf, the value set here is ignored.";
        }
        leaf stdout {
          type empty;
          description
            "If present write output to stdout, useful together
             with the --foreground flag to ncs.";
        }
      }
      leaf connect-time {
        tailf:hidden "debug";
        type string;
        units "seconds";
        // NCS drop default statement
        description
          "The time NCS waits for the Java VM to connect to NCS
           during a synchronous startup of NCS.

           If the timer expires the action defined in
           'synchronization-timeout-action' is taken.";
      }
      leaf initialization-time {
        tailf:hidden "debug";
        type string;
        units "seconds";
        // NCS drop default statement
        description
          "The time NCS waits for each NCS package component to
           initialize itself.

           If the timer expires the action defined in
           'synchronization-timeout-action' is taken.";
      }
      leaf synchronization-timeout-action {
        tailf:hidden "debug";
        type string;
        // NCS drop default statement
        description
          "The action NCS takes if any of the timers 'connect-time' or
           'initialization-time' expires.";
      }
      container exception-error-message {
        tailf:hidden "debug";
        leaf verbosity {
          type ncs_template_error-verbosity-type;
          description
            "Verbosity level value for error messages in the Java VM.";
        }
      }
      container java-logging {
        list logger {
          // NCS patched for predictable order
          ordered-by user;
          key "logger-name";
          description
            "Each entry in this list holds one representation of a logger with
             a specific level defined by log-level-type. The logger-name
             is the name of a Java package.  logger-name can thus be for
             example com.tailf.maapi, or com.tailf etc.";
          leaf logger-name {
            type string;
            // NCS drop mandatory statement
            description
              "The name of the Java package for which this logger
               entry applies.";
          }
          leaf level {
            type ncs_template_log-level-type;
            // NCS drop mandatory statement
            description
              "Corresponding log-level for a specific logger.";
          }
        }
      }
      container jmx {
        tailf:hidden "debug";
        presence "Start a Java Management Extensions (JMX) Agent in the Java VM";
        leaf jndi-address {
          type string;
          // NCS drop default statement
          description
            "The hostname or ip for the RMI registry";
        }
        leaf jndi-port {
          type string;
          // NCS drop default statement
          description
            "The port for the RMI registry";
        }
        leaf jmx-address {
          type string;
          // NCS drop default statement
          description
            "The hostname or ip for the JMX RMI server";
        }
        leaf jmx-port {
          type string;
          // NCS drop default statement
          description
            "The port for the JMX RMI server";
        }
      }
      // NCS drop config false leaf 'start-status'
      // NCS drop config false leaf status
    }
  }
  augment "/ncs-internal:compliance/ncs-internal:template/ncs-internal:ned-id/ncs-internal:config" {
    container java-vm {
      description
        "Configuration parameters to control various properties of the
         Java application code, e.g., logging, and statistics data about
         the Java application code.";
      container stdout-capture {
        tailf:hidden "debug";
        description
          "Capture stdout and stderr from the Java VM.

           Only applicable if auto-start is 'true'.";
        leaf enabled {
          type string;
          // NCS drop default statement
          description
            "NOTE: If a value is set for
             /ncs-config/java-vm/stdout-capture/enabled
             in ncs.conf, the value set here is ignored.";
        }
        leaf file {
          type string;
          // NCS drop default statement
          description
            "Write Java VM output to filename.

             NOTE: If a value is set for
             /ncs-config/java-vm/stdout-capture/file
             in ncs.conf, the value set here is ignored.";
        }
        leaf stdout {
          type empty;
          description
            "If present write output to stdout, useful together
             with the --foreground flag to ncs.";
        }
      }
      leaf connect-time {
        tailf:hidden "debug";
        type string;
        units "seconds";
        // NCS drop default statement
        description
          "The time NCS waits for the Java VM to connect to NCS
           during a synchronous startup of NCS.

           If the timer expires the action defined in
           'synchronization-timeout-action' is taken.";
      }
      leaf initialization-time {
        tailf:hidden "debug";
        type string;
        units "seconds";
        // NCS drop default statement
        description
          "The time NCS waits for each NCS package component to
           initialize itself.

           If the timer expires the action defined in
           'synchronization-timeout-action' is taken.";
      }
      leaf synchronization-timeout-action {
        tailf:hidden "debug";
        type string;
        // NCS drop default statement
        description
          "The action NCS takes if any of the timers 'connect-time' or
           'initialization-time' expires.";
      }
      container exception-error-message {
        tailf:hidden "debug";
        leaf verbosity {
          type ncs_compliance_template_error-verbosity-type;
          description
            "Verbosity level value for error messages in the Java VM.";
        }
      }
      container java-logging {
        list logger {
          // NCS patched for predictable order
          ordered-by user;
          key "logger-name";
          description
            "Each entry in this list holds one representation of a logger with
             a specific level defined by log-level-type. The logger-name
             is the name of a Java package.  logger-name can thus be for
             example com.tailf.maapi, or com.tailf etc.";
          leaf logger-name {
            type string;
            // NCS drop mandatory statement
            description
              "The name of the Java package for which this logger
               entry applies.";
          }
          leaf level {
            type ncs_compliance_template_log-level-type;
            // NCS drop mandatory statement
            description
              "Corresponding log-level for a specific logger.";
          }
        }
      }
      container jmx {
        tailf:hidden "debug";
        presence "Start a Java Management Extensions (JMX) Agent in the Java VM";
        leaf jndi-address {
          type string;
          // NCS drop default statement
          description
            "The hostname or ip for the RMI registry";
        }
        leaf jndi-port {
          type string;
          // NCS drop default statement
          description
            "The port for the RMI registry";
        }
        leaf jmx-address {
          type string;
          // NCS drop default statement
          description
            "The hostname or ip for the JMX RMI server";
        }
        leaf jmx-port {
          type string;
          // NCS drop default statement
          description
            "The port for the JMX RMI server";
        }
      }
      // NCS drop config false leaf 'start-status'
      // NCS drop config false leaf status
    }
  }
}
