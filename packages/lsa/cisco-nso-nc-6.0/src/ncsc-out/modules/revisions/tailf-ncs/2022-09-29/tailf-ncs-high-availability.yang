submodule tailf-ncs-high-availability {
  // Generated by yanger -t ncs
  tailf:mount-id "cisco-nso-nc-6.0:cisco-nso-nc-6.0";

  yang-version 1.1;
  belongs-to tailf-ncs {
    prefix ncs;
  }

  import ietf-inet-types {
    prefix inet;
  }
  import tailf-common {
    prefix tailf;
  }
  import tailf-ncs-internal-mount {
    prefix ncs-internal;
  }

  description
    "This submodule contains a collection of YANG definitions for
     defining and managing NCS High Availability setups.

     Copyright 2020-2022 Cisco Systems, Inc.

     All rights reserved.
     Permission is hereby granted to redistribute this file without
     modification.";

  revision 2022-09-29 {
    description
      "Released as part of NCS-6.0.

       Non-backwards-compatible change have been introduced.

       Update descriptions to use bias-free language.

       Rename the 'master' and 'slave' enums in the 'ha-role' typedef
       to 'primary' and 'secondary'.

       Replace the 'be-slave-result', 'master-id', and 'connected-slave'
       leaves in /high-availability/status with the 'be-secondary-result',
       'primary-id' and 'connected-secondary' leaves.

       Replace the 'failover-master' leaf with the 'failover-primary' leaf
       in /high-availability/ha-node.

       Replace the 'reconnect-slaves' leaf with the 'reconnect-secondaries'
       leaf in /high-availability/settings.

       Replace the 'be-master' and 'be-slave-to' actions with the
       'be-primary' and 'be-secondary-to' actions.

       Editorial changes replacing NSO with NCS.";
  }
  revision 2022-04-12 {
    description
      "Released as part of NCS-5.8.

       Added default value for /high-availability/settings/consensus/enabled.";
  }
  revision 2021-12-17 {
    description
      "Released as part of NCS-5.7.

       Non-backwards-compatible changes have been introduced.

       Added /high-availability/read-only action to enable/disable read-only
       mode.

       Added /high-availability/status/read-only-mode config false leaf
       to show whether read-only mode is enabled/disabled.

       Added /high-availability/settings/consensus/{enabled,algorithm}
       config true leafs to allow algorithms to reach consensus of one
       active master at any time.

       Added constraint under /high-availability/settings/enable-failover.

       Changed default value to 'true' for
       /high-availability/settings/reconnect-slaves";
  }
  revision 2020-06-25 {
    description
      "Released as part of NCS-5.4.

       Initial revision";
  }

  typedef ncs_compliance_template_ha-role {
    type string;
  }

  typedef ncs_template_ha-role {
    type string;
  }

  typedef ncs_rpc_notif_ha-role {
    type enumeration {
      enum "none" {
        tailf:code-name "ha-none";
      }
      enum "secondary";
      enum "primary";
    }
  }

  typedef live_ncs_ha-role {
    type enumeration {
      enum "none" {
        tailf:code-name "ha-none";
      }
      enum "secondary";
      enum "primary";
    }
  }

  typedef ha-role {
    type enumeration {
      enum "none" {
        tailf:code-name "ha-none";
      }
      enum "secondary";
      enum "primary";
    }
  }

  augment "/ncs-internal:devices/ncs-internal:device/ncs-internal:config" {
    container high-availability {
      tailf:ncs-device-type "netconf";
      tailf:display-when "not(../../ncs-internal:module) or ../../ncs-internal:module[ncs-internal:name='tailf-ncs']";
      description
        "Configuration, status and actions concerning NCS Built-in HA";
      leaf token {
        tailf:ned-ignore-compare-config;
        type tailf:aes-256-cfb-128-encrypted-string;
      }
      // NCS drop config false leaf enabled
      // NCS drop config false container status
      list ha-node {
        key "id";
        unique "address";
        leaf id {
          mandatory true;
          type string;
        }
        leaf address {
          description
            "Ip Address of the ncs instance";
          type inet:ip-address;
          mandatory true;
        }
        leaf nominal-role {
          description
            "Default HA-role of node";
          type ncs:ha-role;
          must "current() != 'primary' or
not(../../ha-node[id != current()/../id][nominal-role = 'primary'])" {
            tailf:xpath-root 3;
            error-message "At most one node can be configured as primary";
          }
        }
        leaf failover-primary {
          when "../nominal-role = 'secondary' and
../../settings/enable-failover ='true'" {
            tailf:xpath-root 3;
          }
          must "current() = 'false' or
not(../../ha-node[id != current()/../id][failover-primary = 'true'])" {
            tailf:xpath-root 3;
            error-message "At most one node can serve as a failover primary";
          }
          type boolean;
          default "false";
        }
      }
      container settings {
        leaf enable-failover {
          description
            "Activates failover for nodes with nominal-role primary
             or nominal role secondary + failover primary set.

             Configuring ../consensus/enabled to 'true' is recommended
             to avoid ending up in a scenario with multiple active
             primaries which are out of sync";
          type boolean;
          default "false";
          must ". = 'false' or
(boolean(../../ha-node[nominal-role='primary']) and
boolean(../../ha-node[failover-primary='true']))" {
            tailf:xpath-root 3;
            error-message "When failover is enabled 1 nominal primary and 1 failover primary must be configured.";
          }
        }
        leaf reconnect-secondaries {
          description
            "If set, nodes assigned as secondary will attempt to
             reconnect to the HA Setup after loss of connection to
             primary";
          type boolean;
          default "true";
        }
        container start-up {
          leaf assume-nominal-role {
            description
              "Controls if a node should attempt to assume its nominal
               role on start-up of NCS or enabling of built-in HA.
               Interacts with join-ha and nominal-role as follows:
               nominal-role primary, join-ha false - assume primary role.
               nominal-role primary, join-ha true - attempt once to query
               configured HA nodes for available primary, if none found
               assume primary role.
               nominal-role secondary, join-ha false - attempt once to
               connect as secondary to ha-node with nominal-role primary.
               nominal-role secondary, join-ha true - query configured ha
               nodes for available primary and attempt to join. Retry
               according to configured interval.";
            type boolean;
            default "false";
          }
          leaf join-ha {
            description
              "If set, a Node with nominal role secondary will attempt join
               the HA setup on startup, by querying configured ha nodes for
               an available primary.

               If assume-nominal-role is false, a node with nominal-role
               primary will also attempt to join as secondary.

               Retries will be made according to configured interval.";
            type boolean;
            default "false";
          }
        }
        leaf reconnect-interval {
          description
            "Interval in seconds between reconnect attempts";
          type uint32;
          default "10";
        }
        leaf reconnect-attempts {
          description
            "Number of attempts to reconnect to lost primary before
             initiating failover";
          type uint32;
          default "3";
        }
        container consensus {
          when "../enable-failover = 'true'" {
            tailf:xpath-root 3;
          }
          leaf enabled {
            must ". = 'false' or
../../reconnect-secondaries = 'true'" {
              tailf:xpath-root 3;
            }
            must ". = 'false' or ../algorithm != 'ncs:rule-based' or
count(../../../ha-node) <= 3" {
              tailf:xpath-root 3;
              error-message "When consensus is enabled with the algorithm 'ncs:rule-based', 2 or 3 HA nodes must be configured.";
            }
            type boolean;
            default "true";
          }
          leaf algorithm {
            // NCS patched to string, due to LSA partial NED
            type string;
            default "rule-based";
          }
        }
      }
      tailf:action be-primary {
        tailf:actionpoint ncsproxy {
          tailf:internal;
        }
        description
          "Order the local node to assume ha role primary";
        // NCS drop tailf:actionpoint
        output {
          leaf result {
            type string;
          }
        }
      }
      tailf:action be-none {
        tailf:actionpoint ncsproxy {
          tailf:internal;
        }
        description
          "Order the local node to assume ha role none";
        // NCS drop tailf:actionpoint
        output {
          leaf result {
            type string;
          }
        }
      }
      tailf:action be-secondary-to {
        tailf:actionpoint ncsproxy {
          tailf:internal;
        }
        description
          "Order the local node to connect as secondary to the provided
           ha node";
        // NCS drop tailf:actionpoint
        input {
          leaf node {
            mandatory true;
            type leafref {
              path "../../ha-node/id";
            }
          }
        }
        output {
          leaf result {
            type string;
          }
        }
      }
      tailf:action local-node-id {
        tailf:actionpoint ncsproxy {
          tailf:internal;
        }
        description
          "Identify the which of the nodes in /high-availability/ha-node
           (if any) corresponds to the local NCS instance";
        // NCS drop tailf:actionpoint
        output {
          leaf id {
            type string;
          }
        }
      }
      tailf:action enable {
        tailf:actionpoint ncsproxy {
          tailf:internal;
        }
        description
          "Enable NCS built in HA and optionally assume a ha role
           according to /high-availability/settings/start-up/
           parameters";
        // NCS drop tailf:actionpoint
        output {
          leaf result {
            type string;
          }
        }
      }
      tailf:action disable {
        tailf:actionpoint ncsproxy {
          tailf:internal;
        }
        description
          "Disable NCS built in HA and assume a ha role none";
        // NCS drop tailf:actionpoint
        output {
          leaf result {
            type string;
          }
        }
      }
      tailf:action read-only {
        tailf:actionpoint ncsproxy {
          tailf:internal;
        }
        description
          "Toggle read-only mode, if the mode is 'true' no
           configuration changes can occur";
        // NCS drop tailf:actionpoint
        input {
          leaf mode {
            type boolean;
            default "true";
          }
        }
      }
    }
  }
  augment "/ncs-internal:devices/ncs-internal:device/ncs-internal:live-status" {
    container high-availability {
      tailf:ncs-device-type "netconf";
      tailf:display-when "not(../../ncs-internal:module) or ../../ncs-internal:module[ncs-internal:name='tailf-ncs'] or (../../ncs-internal:live-status-protocol[not(ncs-internal:capability)]) or (../../ncs-internal:live-status-protocol/ncs-internal:capability/ncs-internal:module[.='tailf-ncs'])";
      description
        "Configuration, status and actions concerning NCS Built-in HA";
      leaf token {
        type tailf:aes-256-cfb-128-encrypted-string;
      }
      leaf enabled {
        description
          "Enabling of NCS Built-in HA";
        type boolean;
        // NCS drop default statement
        // NCS drop tailf:cdb-oper
      }
      container status {
        description
          "Status of NCS HA";
        // NCS drop when statement
        // NCS drop tailf:callpoint
        leaf mode {
          description
            "Current active HA role";
          type ncs:live_ncs_ha-role;
        }
        leaf current-id {
          description
            "Currently active HA ID";
          // NCS drop when statement
          type string;
        }
        leaf assigned-role {
          description
            "Role assigned by action, failover or startup";
          type ncs:live_ncs_ha-role;
        }
        leaf be-secondary-result {
          description
            "Result of latest attempt to connect to as secondary";
          type string;
        }
        leaf primary-id {
          description
            "Id of assigned primary node";
          type string;
        }
        leaf read-only-mode {
          description
            "Write transactions are disallowed while
             read-only-mode is true";
          type boolean;
          // NCS drop default statement
        }
        list connected-secondary {
          description
            "HA ids of secondary nodes currently connected to this node";
          key "id";
          leaf id {
            description
              "HA Id of connected secondary node";
            type string;
          }
          leaf address {
            description
              "IP Address of connected secondary node";
            type inet:ip-address;
          }
          status deprecated;
        }
      }
      list ha-node {
        key "id";
        unique "address";
        leaf id {
          // NCS drop mandatory statement
          type string;
        }
        leaf address {
          description
            "Ip Address of the ncs instance";
          type inet:ip-address;
          // NCS drop mandatory statement
        }
        leaf nominal-role {
          description
            "Default HA-role of node";
          type ncs:live_ncs_ha-role;
          // NCS drop must statement
        }
        leaf failover-primary {
          // NCS drop when statement
          // NCS drop must statement
          type boolean;
          // NCS drop default statement
        }
      }
      container settings {
        leaf enable-failover {
          description
            "Activates failover for nodes with nominal-role primary
             or nominal role secondary + failover primary set.

             Configuring ../consensus/enabled to 'true' is recommended
             to avoid ending up in a scenario with multiple active
             primaries which are out of sync";
          type boolean;
          // NCS drop default statement
          // NCS drop must statement
        }
        leaf reconnect-secondaries {
          description
            "If set, nodes assigned as secondary will attempt to
             reconnect to the HA Setup after loss of connection to
             primary";
          type boolean;
          // NCS drop default statement
        }
        container start-up {
          leaf assume-nominal-role {
            description
              "Controls if a node should attempt to assume its nominal
               role on start-up of NCS or enabling of built-in HA.
               Interacts with join-ha and nominal-role as follows:
               nominal-role primary, join-ha false - assume primary role.
               nominal-role primary, join-ha true - attempt once to query
               configured HA nodes for available primary, if none found
               assume primary role.
               nominal-role secondary, join-ha false - attempt once to
               connect as secondary to ha-node with nominal-role primary.
               nominal-role secondary, join-ha true - query configured ha
               nodes for available primary and attempt to join. Retry
               according to configured interval.";
            type boolean;
            // NCS drop default statement
          }
          leaf join-ha {
            description
              "If set, a Node with nominal role secondary will attempt join
               the HA setup on startup, by querying configured ha nodes for
               an available primary.

               If assume-nominal-role is false, a node with nominal-role
               primary will also attempt to join as secondary.

               Retries will be made according to configured interval.";
            type boolean;
            // NCS drop default statement
          }
        }
        leaf reconnect-interval {
          description
            "Interval in seconds between reconnect attempts";
          type uint32;
          // NCS drop default statement
        }
        leaf reconnect-attempts {
          description
            "Number of attempts to reconnect to lost primary before
             initiating failover";
          type uint32;
          // NCS drop default statement
        }
        container consensus {
          // NCS drop when statement
          leaf enabled {
            // NCS drop must statement
            // NCS drop must statement
            type boolean;
            // NCS drop default statement
          }
          leaf algorithm {
            // NCS patched to string, due to LSA partial NED
            type string;
            // NCS drop default statement
          }
        }
      }
      tailf:action be-primary {
        tailf:actionpoint ncsproxy {
          tailf:internal;
        }
        description
          "Order the local node to assume ha role primary";
        // NCS drop tailf:actionpoint
        output {
          leaf result {
            type string;
          }
        }
      }
      tailf:action be-none {
        tailf:actionpoint ncsproxy {
          tailf:internal;
        }
        description
          "Order the local node to assume ha role none";
        // NCS drop tailf:actionpoint
        output {
          leaf result {
            type string;
          }
        }
      }
      tailf:action be-secondary-to {
        tailf:actionpoint ncsproxy {
          tailf:internal;
        }
        description
          "Order the local node to connect as secondary to the provided
           ha node";
        // NCS drop tailf:actionpoint
        input {
          leaf node {
            mandatory true;
            type leafref {
              path "../../ha-node/id";
            }
          }
        }
        output {
          leaf result {
            type string;
          }
        }
      }
      tailf:action local-node-id {
        tailf:actionpoint ncsproxy {
          tailf:internal;
        }
        description
          "Identify the which of the nodes in /high-availability/ha-node
           (if any) corresponds to the local NCS instance";
        // NCS drop tailf:actionpoint
        output {
          leaf id {
            type string;
          }
        }
      }
      tailf:action enable {
        tailf:actionpoint ncsproxy {
          tailf:internal;
        }
        description
          "Enable NCS built in HA and optionally assume a ha role
           according to /high-availability/settings/start-up/
           parameters";
        // NCS drop tailf:actionpoint
        output {
          leaf result {
            type string;
          }
        }
      }
      tailf:action disable {
        tailf:actionpoint ncsproxy {
          tailf:internal;
        }
        description
          "Disable NCS built in HA and assume a ha role none";
        // NCS drop tailf:actionpoint
        output {
          leaf result {
            type string;
          }
        }
      }
      tailf:action read-only {
        tailf:actionpoint ncsproxy {
          tailf:internal;
        }
        description
          "Toggle read-only mode, if the mode is 'true' no
           configuration changes can occur";
        // NCS drop tailf:actionpoint
        input {
          leaf mode {
            type boolean;
            default "true";
          }
        }
      }
    }
  }
  augment "/ncs-internal:devices/ncs-internal:template/ncs-internal:ned-id/ncs-internal:config" {
    container high-availability {
      description
        "Configuration, status and actions concerning NCS Built-in HA";
      leaf token {
        type string;
      }
      // NCS drop config false leaf enabled
      // NCS drop config false container status
      list ha-node {
        // NCS patched for predictable order
        ordered-by user;
        key "id";
        unique "address";
        leaf id {
          // NCS drop mandatory statement
          type string;
        }
        leaf address {
          description
            "Ip Address of the ncs instance";
          type string;
          // NCS drop mandatory statement
        }
        leaf nominal-role {
          description
            "Default HA-role of node";
          type ncs:ncs_template_ha-role;
          // NCS drop must statement
        }
        leaf failover-primary {
          // NCS drop when statement
          // NCS drop must statement
          type string;
          // NCS drop default statement
        }
      }
      container settings {
        leaf enable-failover {
          description
            "Activates failover for nodes with nominal-role primary
             or nominal role secondary + failover primary set.

             Configuring ../consensus/enabled to 'true' is recommended
             to avoid ending up in a scenario with multiple active
             primaries which are out of sync";
          type string;
          // NCS drop default statement
          // NCS drop must statement
        }
        leaf reconnect-secondaries {
          description
            "If set, nodes assigned as secondary will attempt to
             reconnect to the HA Setup after loss of connection to
             primary";
          type string;
          // NCS drop default statement
        }
        container start-up {
          leaf assume-nominal-role {
            description
              "Controls if a node should attempt to assume its nominal
               role on start-up of NCS or enabling of built-in HA.
               Interacts with join-ha and nominal-role as follows:
               nominal-role primary, join-ha false - assume primary role.
               nominal-role primary, join-ha true - attempt once to query
               configured HA nodes for available primary, if none found
               assume primary role.
               nominal-role secondary, join-ha false - attempt once to
               connect as secondary to ha-node with nominal-role primary.
               nominal-role secondary, join-ha true - query configured ha
               nodes for available primary and attempt to join. Retry
               according to configured interval.";
            type string;
            // NCS drop default statement
          }
          leaf join-ha {
            description
              "If set, a Node with nominal role secondary will attempt join
               the HA setup on startup, by querying configured ha nodes for
               an available primary.

               If assume-nominal-role is false, a node with nominal-role
               primary will also attempt to join as secondary.

               Retries will be made according to configured interval.";
            type string;
            // NCS drop default statement
          }
        }
        leaf reconnect-interval {
          description
            "Interval in seconds between reconnect attempts";
          type string;
          // NCS drop default statement
        }
        leaf reconnect-attempts {
          description
            "Number of attempts to reconnect to lost primary before
             initiating failover";
          type string;
          // NCS drop default statement
        }
        container consensus {
          // NCS drop when statement
          leaf enabled {
            // NCS drop must statement
            // NCS drop must statement
            type string;
            // NCS drop default statement
          }
          leaf algorithm {
            type string;
            // NCS drop default statement
          }
        }
      }
    }
  }
  augment "/ncs-internal:compliance/ncs-internal:template/ncs-internal:ned-id/ncs-internal:config" {
    container high-availability {
      description
        "Configuration, status and actions concerning NCS Built-in HA";
      leaf token {
        type string;
      }
      // NCS drop config false leaf enabled
      // NCS drop config false container status
      list ha-node {
        // NCS patched for predictable order
        ordered-by user;
        key "id";
        unique "address";
        leaf id {
          // NCS drop mandatory statement
          type string;
        }
        leaf address {
          description
            "Ip Address of the ncs instance";
          type string;
          // NCS drop mandatory statement
        }
        leaf nominal-role {
          description
            "Default HA-role of node";
          type ncs:ncs_compliance_template_ha-role;
          // NCS drop must statement
        }
        leaf failover-primary {
          // NCS drop when statement
          // NCS drop must statement
          type string;
          // NCS drop default statement
        }
      }
      container settings {
        leaf enable-failover {
          description
            "Activates failover for nodes with nominal-role primary
             or nominal role secondary + failover primary set.

             Configuring ../consensus/enabled to 'true' is recommended
             to avoid ending up in a scenario with multiple active
             primaries which are out of sync";
          type string;
          // NCS drop default statement
          // NCS drop must statement
        }
        leaf reconnect-secondaries {
          description
            "If set, nodes assigned as secondary will attempt to
             reconnect to the HA Setup after loss of connection to
             primary";
          type string;
          // NCS drop default statement
        }
        container start-up {
          leaf assume-nominal-role {
            description
              "Controls if a node should attempt to assume its nominal
               role on start-up of NCS or enabling of built-in HA.
               Interacts with join-ha and nominal-role as follows:
               nominal-role primary, join-ha false - assume primary role.
               nominal-role primary, join-ha true - attempt once to query
               configured HA nodes for available primary, if none found
               assume primary role.
               nominal-role secondary, join-ha false - attempt once to
               connect as secondary to ha-node with nominal-role primary.
               nominal-role secondary, join-ha true - query configured ha
               nodes for available primary and attempt to join. Retry
               according to configured interval.";
            type string;
            // NCS drop default statement
          }
          leaf join-ha {
            description
              "If set, a Node with nominal role secondary will attempt join
               the HA setup on startup, by querying configured ha nodes for
               an available primary.

               If assume-nominal-role is false, a node with nominal-role
               primary will also attempt to join as secondary.

               Retries will be made according to configured interval.";
            type string;
            // NCS drop default statement
          }
        }
        leaf reconnect-interval {
          description
            "Interval in seconds between reconnect attempts";
          type string;
          // NCS drop default statement
        }
        leaf reconnect-attempts {
          description
            "Number of attempts to reconnect to lost primary before
             initiating failover";
          type string;
          // NCS drop default statement
        }
        container consensus {
          // NCS drop when statement
          leaf enabled {
            // NCS drop must statement
            // NCS drop must statement
            type string;
            // NCS drop default statement
          }
          leaf algorithm {
            type string;
            // NCS drop default statement
          }
        }
      }
    }
  }

  identity rule-based {
    base consensus-algorithm;
    description
      "If all secondaries disconnect from the nominal primary, the primary
       will change role to 'none'. If the failover-primary is active
       but without connected secondaries it will enable read-only mode,
       once a secondary joins the failover-primary, the failover-primary
       will enable read-write mode.

       See the description for the /high-availability/read-only
       action for more info on read-only mode.";
  }

  identity consensus-algorithm {
    description
      "Means to ensure there is only one active primary.";
  }
}
