submodule tailf-ncs-customers {
  // Generated by yanger -t ncs
  tailf:mount-id "cisco-nso-nc-6.0:cisco-nso-nc-6.0";

  yang-version 1.1;
  belongs-to tailf-ncs {
    prefix ncs;
  }

  import tailf-common {
    prefix tailf;
  }
  import tailf-ncs-internal-mount {
    prefix ncs-internal;
  }

  organization
    "Tail-f Systems";
  description
    "This submodule contains a collection of YANG definitions
     for configuring customers.

     Copyright 2012 Cisco Systems, Inc.
     All rights reserved.
     Permission is hereby granted to redistribute this file without
     modification.";

  revision 2012-08-30 {
    description
      "Released as part of NCS-2.0.";
  }

  augment "/ncs-internal:devices/ncs-internal:device/ncs-internal:config" {
    container customers {
      tailf:ncs-device-type "netconf";
      tailf:display-when "not(../../ncs-internal:module) or ../../ncs-internal:module[ncs-internal:name='tailf-ncs']";
      tailf:info
        "Customers using services";
      list customer {
        tailf:info
          "Show customers";
        key "id";
        reference "TMForumPhaseVIII::SID Phase VIII::Customer Domain";
        leaf id {
          tailf:info
            "Unique customer id";
          type string;
          reference "Customer ABE::id";
        }
        leaf rank {
          tailf:info
            "Customer rank";
          type uint8;
          reference "Customer ABE::rank";
        }
        leaf status {
          tailf:info
            "Customer status";
          type enumeration {
            enum "active";
            enum "inactive";
            enum "prospective";
          }
          reference "Customer ABE::status";
        }
        // NCS drop config false leaf-list 'customer-service'
        container properties {
          tailf:info
            "Specific customer properties";
          description
            "This container can be augmented with specific customer
             properties.";
        }
      }
    }
  }
  augment "/ncs-internal:devices/ncs-internal:device/ncs-internal:live-status" {
    container customers {
      tailf:ncs-device-type "netconf";
      tailf:display-when "not(../../ncs-internal:module) or ../../ncs-internal:module[ncs-internal:name='tailf-ncs'] or (../../ncs-internal:live-status-protocol[not(ncs-internal:capability)]) or (../../ncs-internal:live-status-protocol/ncs-internal:capability/ncs-internal:module[.='tailf-ncs'])";
      tailf:info
        "Customers using services";
      list customer {
        tailf:info
          "Show customers";
        key "id";
        reference "TMForumPhaseVIII::SID Phase VIII::Customer Domain";
        leaf id {
          tailf:info
            "Unique customer id";
          type string;
          reference "Customer ABE::id";
        }
        leaf rank {
          tailf:info
            "Customer rank";
          type uint8;
          reference "Customer ABE::rank";
        }
        leaf status {
          tailf:info
            "Customer status";
          type enumeration {
            enum "active";
            enum "inactive";
            enum "prospective";
          }
          reference "Customer ABE::status";
        }
        leaf-list customer-service {
          tailf:info
            "Customer facing services";
          type string;
          description
            "A list of references to /services/customer-service.";
          // NCS drop tailf:callpoint
        }
        container properties {
          tailf:info
            "Specific customer properties";
          description
            "This container can be augmented with specific customer
             properties.";
        }
      }
    }
  }
  augment "/ncs-internal:devices/ncs-internal:template/ncs-internal:ned-id/ncs-internal:config" {
    container customers {
      list customer {
        // NCS patched for predictable order
        ordered-by user;
        key "id";
        reference "TMForumPhaseVIII::SID Phase VIII::Customer Domain";
        leaf id {
          type string;
          reference "Customer ABE::id";
        }
        leaf rank {
          type string;
          reference "Customer ABE::rank";
        }
        leaf status {
          type string;
          reference "Customer ABE::status";
        }
        // NCS drop config false leaf-list 'customer-service'
        container properties {
          description
            "This container can be augmented with specific customer
             properties.";
        }
      }
    }
  }
  augment "/ncs-internal:compliance/ncs-internal:template/ncs-internal:ned-id/ncs-internal:config" {
    container customers {
      list customer {
        // NCS patched for predictable order
        ordered-by user;
        key "id";
        reference "TMForumPhaseVIII::SID Phase VIII::Customer Domain";
        leaf id {
          type string;
          reference "Customer ABE::id";
        }
        leaf rank {
          type string;
          reference "Customer ABE::rank";
        }
        leaf status {
          type string;
          reference "Customer ABE::status";
        }
        // NCS drop config false leaf-list 'customer-service'
        container properties {
          description
            "This container can be augmented with specific customer
             properties.";
        }
      }
    }
  }
}
