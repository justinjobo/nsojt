submodule tailf-ncs-ssh {
  // Generated by yanger -t ncs
  tailf:mount-id "cisco-nso-nc-6.0:cisco-nso-nc-6.0";

  yang-version 1.1;
  belongs-to tailf-ncs {
    prefix ncs;
  }

  import tailf-common {
    prefix tailf;
  }
  import ietf-yang-types {
    prefix yang;
  }
  import tailf-ncs-internal-mount {
    prefix ncs-internal;
  }

  organization
    "Tail-f Systems";
  description
    "This submodule contains configuration items for SSH connections.

     Copyright 2014-2021 Cisco Systems, Inc.
     All rights reserved.
     Permission is hereby granted to redistribute this file without
     modification.";

  revision 2021-09-02 {
    description
      "Released as part of NCS-5.6.

       Added the ssh-algorithms grouping.

       Added the ssh-public-key-algorithm, ssh-kex-algorithm,
       ssh-cipher-algorithm, ssh-mac-algorithm, ssh-compression-algorithm
       and dh-group-size-type typedefs.

       Added ssh-ed448 enum to ssh-key-algorithm typedef.";
  }
  revision 2020-11-26 {
    description
      "Released as part of NCS-5.5.

       Added ecdsa-256, ecdsa-384, ecdsa-521 enums to the ssh-key-algorithm
       typedef.";
  }
  revision 2019-11-28 {
    description
      "Released as part of NCS-5.3.

       Changed typedef ssh-private-key to use
       tailf:aes-256-cfb-128-encrypted-string.

       Changed grouping public-key-auth:
        passphrase was changed from tailf:aes-cfb-128-encrypted-string
        to tailf:aes-256-cfb-128-encrypted-string.

       ssh/private-key/passphrase was changed from
       tailf:aes-cfb-128-encrypted-string
       to tailf:aes-256-cfb-128-encrypted-string.

       Added ssh-ed25519 enum to the ssh-key-algorithm
       typedef.";
  }
  revision 2016-12-12 {
    description
      "Released as part of NCS-4.2.2.

       Changed typedef ssh-private-key to
       upgrade of pre-4.2 private keys.";
  }
  revision 2016-01-01 {
    description
      "Released as part of NCS-4.1.1.

       Added the 'updated-uncommitted' enum value for the 'result' leaf
       in the fetch-ssh-host-keys-result grouping and updated the
       description for the fetch-host-keys action.";
  }
  revision 2014-06-30 {
    description
      "Initial revision, released as part of NCS-3.2.";
  }

  typedef ncs_compliance_template_ssh-host-key-verification-level {
    description
      "This enumeration is used to specify how strictly the verification of
       SSH host keys is done.";
    type string;
  }

  typedef ncs_compliance_template_ssh-key-algorithm {
    type string;
  }

  typedef ncs_compliance_template_ssh-public-key-algorithm {
    type string;
  }

  typedef ncs_compliance_template_ssh-kex-algorithm {
    type string;
  }

  typedef ncs_compliance_template_ssh-cipher-algorithm {
    type string;
  }

  typedef ncs_compliance_template_ssh-mac-algorithm {
    type string;
  }

  typedef ncs_compliance_template_ssh-compression-algorithm {
    type string;
  }

  typedef ncs_compliance_template_ssh-host-key {
    type string;
  }

  typedef ncs_compliance_template_ssh-private-key-iv {
    type string;
  }

  typedef ncs_compliance_template_dh-group-size-type {
    type string;
  }

  typedef ncs_template_ssh-host-key-verification-level {
    description
      "This enumeration is used to specify how strictly the verification of
       SSH host keys is done.";
    type string;
  }

  typedef ncs_template_ssh-key-algorithm {
    type string;
  }

  typedef ncs_template_ssh-public-key-algorithm {
    type string;
  }

  typedef ncs_template_ssh-kex-algorithm {
    type string;
  }

  typedef ncs_template_ssh-cipher-algorithm {
    type string;
  }

  typedef ncs_template_ssh-mac-algorithm {
    type string;
  }

  typedef ncs_template_ssh-compression-algorithm {
    type string;
  }

  typedef ncs_template_ssh-host-key {
    type string;
  }

  typedef ncs_template_ssh-private-key-iv {
    type string;
  }

  typedef ncs_template_dh-group-size-type {
    type string;
  }

  typedef ncs_rpc_notif_ssh-host-key-verification-level {
    description
      "This enumeration is used to specify how strictly the verification of
       SSH host keys is done.";
    type enumeration {
      enum "reject-unknown" {
        tailf:info
          "Reject unknown host keys";
        description
          "With this setting, the SSH host key provided by the device or
           cluster node must already be known.";
      }
      enum "reject-mismatch" {
        tailf:info
          "Reject host keys that do not match the stored key";
        description
          "With this setting, the SSH host key provided by the device or
           cluster node may be unknown, but it must not be different from
           a 'known' key for the same key algorithm.";
      }
      enum "none" {
        tailf:info
          "Accept any host key";
        description
          "With this setting, no SSH host key verification is done - the
           key provided by the device or cluster node may be either unknown
           or different from a 'known' key for the same key algorithm.";
      }
    }
  }

  typedef ncs_rpc_notif_ssh-key-algorithm {
    type enumeration {
      enum "ssh-dss" {
        tailf:info
          "SSH DSA key";
      }
      enum "ssh-rsa" {
        tailf:info
          "SSH RSA key";
      }
      enum "ssh-ed25519" {
        tailf:info
          "SSH EDDSA (ED25519) key";
      }
      enum "ecdsa-256" {
        tailf:info
          "SSH EcDSA-SHA2-NISTP256 key";
      }
      enum "ecdsa-384" {
        tailf:info
          "SSH EcDSA-SHA2-NISTP384 key";
      }
      enum "ecdsa-521" {
        tailf:info
          "SSH EcDSA-SHA2-NISTP521 key";
      }
      enum "ssh-ed448" {
        tailf:info
          "SSH EDDSA (ED448) key";
      }
    }
  }

  typedef ncs_rpc_notif_ssh-public-key-algorithm {
    type enumeration {
      enum "ssh-dss" {
        tailf:info
          "SSH DSA key algorithm";
      }
      enum "ssh-rsa" {
        tailf:info
          "SSH RSA key algorithm";
      }
      enum "ssh-ed25519" {
        tailf:info
          "SSH EDDSA (ED25519) key algorithm";
      }
      enum "ecdsa-sha2-nistp256" {
        tailf:info
          "SSH EcDSA-SHA2-NISTP256 key algorithm";
      }
      enum "ecdsa-sha2-nistp384" {
        tailf:info
          "SSH EcDSA-SHA2-NISTP384 key algorithm";
      }
      enum "ecdsa-sha2-nistp521" {
        tailf:info
          "SSH EcDSA-SHA2-NISTP521 key algorithm";
      }
      enum "ssh-ed448" {
        tailf:info
          "SSH EDDSA (ED448) key algorithm";
      }
      enum "rsa-sha2-256" {
        tailf:info
          "SSH RSA-SHA2-256 key algorithm";
      }
      enum "rsa-sha2-512" {
        tailf:info
          "SSH RSA-SHA2-256 key algorithm";
      }
    }
  }

  typedef ncs_rpc_notif_ssh-kex-algorithm {
    type union {
      type enumeration {
        enum "diffie-hellman-group-exchange-sha1" {
          tailf:info
            "diffie-hellman-group-exchange-sha1";
        }
        enum "diffie-hellman-group-exchange-sha256" {
          tailf:info
            "diffie-hellman-group-exchange-sha256";
        }
        enum "diffie-hellman-group1-sha1" {
          tailf:info
            "diffie-hellman-group1-sha1";
        }
        enum "diffie-hellman-group14-sha1" {
          tailf:info
            "diffie-hellman-group14-sha1";
        }
        enum "diffie-hellman-group14-sha256" {
          tailf:info
            "diffie-hellman-group14-sha256";
        }
        enum "diffie-hellman-group14-sha256@ssh.com" {
          tailf:code-name "diffie-hellman-group14-sha256-ssh-com";
          tailf:info
            "diffie-hellman-group14-sha256@ssh.com";
        }
        enum "diffie-hellman-group15-sha256" {
          tailf:info
            "diffie-hellman-group15-sha256";
        }
        enum "diffie-hellman-group15-sha256@ssh.com" {
          tailf:code-name "diffie-hellman-group15-sha256-ssh-com";
          tailf:info
            "diffie-hellman-group15-sha256@ssh.com";
        }
        enum "diffie-hellman-group15-sha384@ssh.com" {
          tailf:code-name "diffie-hellman-group15-sha384-ssh-com";
          tailf:info
            "diffie-hellman-group15-sha384@ssh.com";
        }
        enum "diffie-hellman-group15-sha512" {
          tailf:info
            "diffie-hellman-group15-sha512";
        }
        enum "diffie-hellman-group16-sha256" {
          tailf:info
            "diffie-hellman-group16-sha256";
        }
        enum "diffie-hellman-group16-sha384@ssh.com" {
          tailf:code-name "diffie-hellman-group16-sha384-ssh-com";
          tailf:info
            "diffie-hellman-group16-sha384@ssh.com";
        }
        enum "diffie-hellman-group16-sha512" {
          tailf:info
            "diffie-hellman-group16-sha512";
        }
        enum "diffie-hellman-group16-sha512@ssh.com" {
          tailf:code-name "diffie-hellman-group16-sha512-ssh-com";
          tailf:info
            "diffie-hellman-group16-sha512@ssh.com";
        }
        enum "diffie-hellman-group17-sha512" {
          tailf:info
            "diffie-hellman-group17-sha512";
        }
        enum "diffie-hellman-group18-sha512" {
          tailf:info
            "diffie-hellman-group18-sha512";
        }
        enum "diffie-hellman-group18-sha512@ssh.com" {
          tailf:code-name "diffie-hellman-group18-sha512-ssh-com";
          tailf:info
            "diffie-hellman-group18-sha512@ssh.com";
        }
        enum "curve448-sha512" {
          tailf:info
            "curve448-sha512";
        }
        enum "curve25519-sha256" {
          tailf:info
            "curve25519-sha256";
        }
        enum "curve25519-sha256@libssh.org" {
          tailf:code-name "curve25519-sha256-libssh-org";
          tailf:info
            "curve25519-sha256@libssh.org";
        }
        enum "curve25519-sha512" {
          tailf:info
            "curve25519-sha512";
        }
        enum "ecdh-sha2-nistp256" {
          tailf:info
            "ecdh-sha2-nistp256";
        }
        enum "ecdh-sha2-nistp384" {
          tailf:info
            "ecdh-sha2-nistp384";
        }
        enum "ecdh-sha2-nistp521" {
          tailf:info
            "ecdh-sha2-nistp521";
        }
        enum "ext-info-c" {
          tailf:info
            "ext-info-c";
        }
      }
      type string;
    }
  }

  typedef ncs_rpc_notif_ssh-cipher-algorithm {
    type union {
      type enumeration {
        enum "3des-cbc" {
          tailf:info
            "3des-cbc";
        }
        enum "3des-ctr" {
          tailf:info
            "3des-ctr";
        }
        enum "aes128-cbc" {
          tailf:info
            "aes128-cbc";
        }
        enum "aes128-ctr" {
          tailf:info
            "aes128-ctr";
        }
        enum "aes128-gcm@openssh.com" {
          tailf:code-name "aes128-gcm-openssh-com";
          tailf:info
            "aes128-gcm@openssh.com";
        }
        enum "aes192-cbc" {
          tailf:info
            "aes192-cbc";
        }
        enum "aes192-ctr" {
          tailf:info
            "aes192-ctr";
        }
        enum "aes256-cbc" {
          tailf:info
            "aes256-cbc";
        }
        enum "aes256-ctr" {
          tailf:info
            "aes256-ctr";
        }
        enum "aes256-gcm@openssh.com" {
          tailf:code-name "aes256-gcm-openssh-com";
          tailf:info
            "aes256-gcm@openssh.com";
        }
        enum "blowfish-cbc" {
          tailf:info
            "blowfish-cbc";
        }
        enum "blowfish-ctr" {
          tailf:info
            "blowfish-ctr";
        }
        enum "cast128-cbc" {
          tailf:info
            "cast128-cbc";
        }
        enum "cast128-ctr" {
          tailf:info
            "cast128-ctr";
        }
        enum "idea-cbc" {
          tailf:info
            "idea-cbc";
        }
        enum "idea-ctr" {
          tailf:info
            "idea-ctr";
        }
        enum "serpent128-cbc" {
          tailf:info
            "serpent128-cbc";
        }
        enum "serpent128-ctr" {
          tailf:info
            "serpent128-ctr";
        }
        enum "serpent192-cbc" {
          tailf:info
            "serpent192-cbc";
        }
        enum "serpent192-ctr" {
          tailf:info
            "serpent192-ctr";
        }
        enum "serpent256-cbc" {
          tailf:info
            "serpent256-cbc";
        }
        enum "serpent256-ctr" {
          tailf:info
            "serpent256-ctr";
        }
        enum "twofish128-cbc" {
          tailf:info
            "twofish128-cbc";
        }
        enum "twofish128-ctr" {
          tailf:info
            "twofish128-ctr";
        }
        enum "twofish192-cbc" {
          tailf:info
            "twofish192-cbc";
        }
        enum "twofish192-ctr" {
          tailf:info
            "twofish192-ctr";
        }
        enum "twofish256-cbc" {
          tailf:info
            "twofish256-cbc";
        }
        enum "twofish256-ctr" {
          tailf:info
            "twofish256-ctr";
        }
        enum "twofish-cbc" {
          tailf:info
            "twofish-cbc";
        }
        enum "arcfour" {
          tailf:info
            "arcfour";
        }
        enum "arcfour128" {
          tailf:info
            "arcfour128";
        }
        enum "arcfour256" {
          tailf:info
            "arcfour256";
        }
        enum "chacha20-poly1305@openssh.com" {
          tailf:code-name "chacha20-poly1305-openssh-com";
          tailf:info
            "chacha20-poly1305@openssh.com";
        }
        enum "AEAD_AES_128_GCM" {
          tailf:code-name "ssh-cipher-aead-aes-128-gcm";
          tailf:info
            "AEAD_AES_128_GCM";
        }
        enum "AEAD_AES_256_GCM" {
          tailf:code-name "ssh-cipher-aead-aes-256-gcm";
          tailf:info
            "AEAD_AES_256_GCM";
        }
      }
      type string;
    }
  }

  typedef ncs_rpc_notif_ssh-mac-algorithm {
    type union {
      type enumeration {
        enum "hmac-md5" {
          tailf:info
            "hmac-md5";
        }
        enum "hmac-md5-etm@openssh.com" {
          tailf:code-name "hmac-md5-etm-openssh-com";
          tailf:info
            "hmac-md5-etm@openssh.com";
        }
        enum "hmac-md5-96" {
          tailf:info
            "hmac-md5-96";
        }
        enum "hmac-md5-96-etm@openssh.com" {
          tailf:code-name "hmac-md5-96-etm-openssh-com";
          tailf:info
            "hmac-md5-96-etm@openssh.com";
        }
        enum "hmac-sha1" {
          tailf:info
            "hmac-sha1";
        }
        enum "hmac-sha1-etm@openssh.com" {
          tailf:code-name "hmac-sha1-etm-openssh-com";
          tailf:info
            "hmac-sha1-etm@openssh.com";
        }
        enum "hmac-sha1-96" {
          tailf:info
            "hmac-sha1-96";
        }
        enum "hmac-sha1-96@openssh.com" {
          tailf:code-name "hmac-sha1-96-openssh-com";
          tailf:info
            "hmac-sha1-96@openssh.com";
        }
        enum "hmac-sha2-256" {
          tailf:info
            "hmac-sha2-256";
        }
        enum "hmac-sha2-256-etm@openssh.com" {
          tailf:code-name "hmac-sha2-256-etm-openssh-com";
          tailf:info
            "hmac-sha2-256-etm@openssh.com";
        }
        enum "hmac-sha2-512" {
          tailf:info
            "hmac-sha2-512";
        }
        enum "hmac-sha2-512-etm@openssh.com" {
          tailf:code-name "hmac-sha2-512-etm-openssh-com";
          tailf:info
            "hmac-sha2-512-etm@openssh.com";
        }
        enum "hmac-ripemd160" {
          tailf:info
            "hmac-ripemd160";
        }
        enum "hmac-ripemd160@openssh.com" {
          tailf:code-name "hmac-ripemd160-openssh-com";
          tailf:info
            "hmac-ripemd160@openssh.com";
        }
        enum "hmac-ripemd160-96" {
          tailf:info
            "hmac-ripemd160-96";
        }
        enum "hmac-ripemd160-etm@openssh.com" {
          tailf:code-name "hmac-ripemd160-etm-openssh-com";
          tailf:info
            "hmac-ripemd160-etm@openssh.com";
        }
        enum "AEAD_AES_128_GCM" {
          tailf:code-name "ssh-mac-aead-aes-128-gcm";
          tailf:info
            "AEAD_AES_128_GCM";
        }
        enum "AEAD_AES_256_GCM" {
          tailf:code-name "ssh-mac-aead-aes-256-gcm";
          tailf:info
            "AEAD_AES_256_GCM";
        }
      }
      type string;
    }
  }

  typedef ncs_rpc_notif_ssh-compression-algorithm {
    type union {
      type enumeration {
        enum "none" {
          tailf:code-name "ssh-compression-none";
          tailf:info
            "No compression";
        }
        enum "zlib" {
          tailf:code-name "ssh-compression-zlib";
          tailf:info
            "ZLIB (LZ77) compression";
        }
        enum "zlib@openssh.com" {
          tailf:code-name "ssh-compression-zlib-openssh-com";
          tailf:info
            "ZLIB (LZ77) compression (OpenSSH version)";
        }
      }
      type string;
    }
  }

  typedef ncs_rpc_notif_ssh-host-key {
    tailf:info
      "SSH public host key";
    type binary;
    // NCS drop tailf:typepoint
  }

  typedef ncs_rpc_notif_ssh-private-key-iv {
    tailf:info
      "SSH private user key";
    type tailf:aes-256-cfb-128-encrypted-string;
    // NCS drop tailf:typepoint
  }

  typedef ncs_rpc_notif_dh-group-size-type {
    type uint32 {
      range "1024 .. 8192";
    }
  }

  typedef live_ncs_ssh-host-key-verification-level {
    description
      "This enumeration is used to specify how strictly the verification of
       SSH host keys is done.";
    type enumeration {
      enum "reject-unknown" {
        tailf:info
          "Reject unknown host keys";
        description
          "With this setting, the SSH host key provided by the device or
           cluster node must already be known.";
      }
      enum "reject-mismatch" {
        tailf:info
          "Reject host keys that do not match the stored key";
        description
          "With this setting, the SSH host key provided by the device or
           cluster node may be unknown, but it must not be different from
           a 'known' key for the same key algorithm.";
      }
      enum "none" {
        tailf:info
          "Accept any host key";
        description
          "With this setting, no SSH host key verification is done - the
           key provided by the device or cluster node may be either unknown
           or different from a 'known' key for the same key algorithm.";
      }
    }
  }

  typedef live_ncs_ssh-key-algorithm {
    type enumeration {
      enum "ssh-dss" {
        tailf:info
          "SSH DSA key";
      }
      enum "ssh-rsa" {
        tailf:info
          "SSH RSA key";
      }
      enum "ssh-ed25519" {
        tailf:info
          "SSH EDDSA (ED25519) key";
      }
      enum "ecdsa-256" {
        tailf:info
          "SSH EcDSA-SHA2-NISTP256 key";
      }
      enum "ecdsa-384" {
        tailf:info
          "SSH EcDSA-SHA2-NISTP384 key";
      }
      enum "ecdsa-521" {
        tailf:info
          "SSH EcDSA-SHA2-NISTP521 key";
      }
      enum "ssh-ed448" {
        tailf:info
          "SSH EDDSA (ED448) key";
      }
    }
  }

  typedef live_ncs_ssh-public-key-algorithm {
    type enumeration {
      enum "ssh-dss" {
        tailf:info
          "SSH DSA key algorithm";
      }
      enum "ssh-rsa" {
        tailf:info
          "SSH RSA key algorithm";
      }
      enum "ssh-ed25519" {
        tailf:info
          "SSH EDDSA (ED25519) key algorithm";
      }
      enum "ecdsa-sha2-nistp256" {
        tailf:info
          "SSH EcDSA-SHA2-NISTP256 key algorithm";
      }
      enum "ecdsa-sha2-nistp384" {
        tailf:info
          "SSH EcDSA-SHA2-NISTP384 key algorithm";
      }
      enum "ecdsa-sha2-nistp521" {
        tailf:info
          "SSH EcDSA-SHA2-NISTP521 key algorithm";
      }
      enum "ssh-ed448" {
        tailf:info
          "SSH EDDSA (ED448) key algorithm";
      }
      enum "rsa-sha2-256" {
        tailf:info
          "SSH RSA-SHA2-256 key algorithm";
      }
      enum "rsa-sha2-512" {
        tailf:info
          "SSH RSA-SHA2-256 key algorithm";
      }
    }
  }

  typedef live_ncs_ssh-kex-algorithm {
    type union {
      type enumeration {
        enum "diffie-hellman-group-exchange-sha1" {
          tailf:info
            "diffie-hellman-group-exchange-sha1";
        }
        enum "diffie-hellman-group-exchange-sha256" {
          tailf:info
            "diffie-hellman-group-exchange-sha256";
        }
        enum "diffie-hellman-group1-sha1" {
          tailf:info
            "diffie-hellman-group1-sha1";
        }
        enum "diffie-hellman-group14-sha1" {
          tailf:info
            "diffie-hellman-group14-sha1";
        }
        enum "diffie-hellman-group14-sha256" {
          tailf:info
            "diffie-hellman-group14-sha256";
        }
        enum "diffie-hellman-group14-sha256@ssh.com" {
          tailf:code-name "diffie-hellman-group14-sha256-ssh-com";
          tailf:info
            "diffie-hellman-group14-sha256@ssh.com";
        }
        enum "diffie-hellman-group15-sha256" {
          tailf:info
            "diffie-hellman-group15-sha256";
        }
        enum "diffie-hellman-group15-sha256@ssh.com" {
          tailf:code-name "diffie-hellman-group15-sha256-ssh-com";
          tailf:info
            "diffie-hellman-group15-sha256@ssh.com";
        }
        enum "diffie-hellman-group15-sha384@ssh.com" {
          tailf:code-name "diffie-hellman-group15-sha384-ssh-com";
          tailf:info
            "diffie-hellman-group15-sha384@ssh.com";
        }
        enum "diffie-hellman-group15-sha512" {
          tailf:info
            "diffie-hellman-group15-sha512";
        }
        enum "diffie-hellman-group16-sha256" {
          tailf:info
            "diffie-hellman-group16-sha256";
        }
        enum "diffie-hellman-group16-sha384@ssh.com" {
          tailf:code-name "diffie-hellman-group16-sha384-ssh-com";
          tailf:info
            "diffie-hellman-group16-sha384@ssh.com";
        }
        enum "diffie-hellman-group16-sha512" {
          tailf:info
            "diffie-hellman-group16-sha512";
        }
        enum "diffie-hellman-group16-sha512@ssh.com" {
          tailf:code-name "diffie-hellman-group16-sha512-ssh-com";
          tailf:info
            "diffie-hellman-group16-sha512@ssh.com";
        }
        enum "diffie-hellman-group17-sha512" {
          tailf:info
            "diffie-hellman-group17-sha512";
        }
        enum "diffie-hellman-group18-sha512" {
          tailf:info
            "diffie-hellman-group18-sha512";
        }
        enum "diffie-hellman-group18-sha512@ssh.com" {
          tailf:code-name "diffie-hellman-group18-sha512-ssh-com";
          tailf:info
            "diffie-hellman-group18-sha512@ssh.com";
        }
        enum "curve448-sha512" {
          tailf:info
            "curve448-sha512";
        }
        enum "curve25519-sha256" {
          tailf:info
            "curve25519-sha256";
        }
        enum "curve25519-sha256@libssh.org" {
          tailf:code-name "curve25519-sha256-libssh-org";
          tailf:info
            "curve25519-sha256@libssh.org";
        }
        enum "curve25519-sha512" {
          tailf:info
            "curve25519-sha512";
        }
        enum "ecdh-sha2-nistp256" {
          tailf:info
            "ecdh-sha2-nistp256";
        }
        enum "ecdh-sha2-nistp384" {
          tailf:info
            "ecdh-sha2-nistp384";
        }
        enum "ecdh-sha2-nistp521" {
          tailf:info
            "ecdh-sha2-nistp521";
        }
        enum "ext-info-c" {
          tailf:info
            "ext-info-c";
        }
      }
      type string;
    }
  }

  typedef live_ncs_ssh-cipher-algorithm {
    type union {
      type enumeration {
        enum "3des-cbc" {
          tailf:info
            "3des-cbc";
        }
        enum "3des-ctr" {
          tailf:info
            "3des-ctr";
        }
        enum "aes128-cbc" {
          tailf:info
            "aes128-cbc";
        }
        enum "aes128-ctr" {
          tailf:info
            "aes128-ctr";
        }
        enum "aes128-gcm@openssh.com" {
          tailf:code-name "aes128-gcm-openssh-com";
          tailf:info
            "aes128-gcm@openssh.com";
        }
        enum "aes192-cbc" {
          tailf:info
            "aes192-cbc";
        }
        enum "aes192-ctr" {
          tailf:info
            "aes192-ctr";
        }
        enum "aes256-cbc" {
          tailf:info
            "aes256-cbc";
        }
        enum "aes256-ctr" {
          tailf:info
            "aes256-ctr";
        }
        enum "aes256-gcm@openssh.com" {
          tailf:code-name "aes256-gcm-openssh-com";
          tailf:info
            "aes256-gcm@openssh.com";
        }
        enum "blowfish-cbc" {
          tailf:info
            "blowfish-cbc";
        }
        enum "blowfish-ctr" {
          tailf:info
            "blowfish-ctr";
        }
        enum "cast128-cbc" {
          tailf:info
            "cast128-cbc";
        }
        enum "cast128-ctr" {
          tailf:info
            "cast128-ctr";
        }
        enum "idea-cbc" {
          tailf:info
            "idea-cbc";
        }
        enum "idea-ctr" {
          tailf:info
            "idea-ctr";
        }
        enum "serpent128-cbc" {
          tailf:info
            "serpent128-cbc";
        }
        enum "serpent128-ctr" {
          tailf:info
            "serpent128-ctr";
        }
        enum "serpent192-cbc" {
          tailf:info
            "serpent192-cbc";
        }
        enum "serpent192-ctr" {
          tailf:info
            "serpent192-ctr";
        }
        enum "serpent256-cbc" {
          tailf:info
            "serpent256-cbc";
        }
        enum "serpent256-ctr" {
          tailf:info
            "serpent256-ctr";
        }
        enum "twofish128-cbc" {
          tailf:info
            "twofish128-cbc";
        }
        enum "twofish128-ctr" {
          tailf:info
            "twofish128-ctr";
        }
        enum "twofish192-cbc" {
          tailf:info
            "twofish192-cbc";
        }
        enum "twofish192-ctr" {
          tailf:info
            "twofish192-ctr";
        }
        enum "twofish256-cbc" {
          tailf:info
            "twofish256-cbc";
        }
        enum "twofish256-ctr" {
          tailf:info
            "twofish256-ctr";
        }
        enum "twofish-cbc" {
          tailf:info
            "twofish-cbc";
        }
        enum "arcfour" {
          tailf:info
            "arcfour";
        }
        enum "arcfour128" {
          tailf:info
            "arcfour128";
        }
        enum "arcfour256" {
          tailf:info
            "arcfour256";
        }
        enum "chacha20-poly1305@openssh.com" {
          tailf:code-name "chacha20-poly1305-openssh-com";
          tailf:info
            "chacha20-poly1305@openssh.com";
        }
        enum "AEAD_AES_128_GCM" {
          tailf:code-name "ssh-cipher-aead-aes-128-gcm";
          tailf:info
            "AEAD_AES_128_GCM";
        }
        enum "AEAD_AES_256_GCM" {
          tailf:code-name "ssh-cipher-aead-aes-256-gcm";
          tailf:info
            "AEAD_AES_256_GCM";
        }
      }
      type string;
    }
  }

  typedef live_ncs_ssh-mac-algorithm {
    type union {
      type enumeration {
        enum "hmac-md5" {
          tailf:info
            "hmac-md5";
        }
        enum "hmac-md5-etm@openssh.com" {
          tailf:code-name "hmac-md5-etm-openssh-com";
          tailf:info
            "hmac-md5-etm@openssh.com";
        }
        enum "hmac-md5-96" {
          tailf:info
            "hmac-md5-96";
        }
        enum "hmac-md5-96-etm@openssh.com" {
          tailf:code-name "hmac-md5-96-etm-openssh-com";
          tailf:info
            "hmac-md5-96-etm@openssh.com";
        }
        enum "hmac-sha1" {
          tailf:info
            "hmac-sha1";
        }
        enum "hmac-sha1-etm@openssh.com" {
          tailf:code-name "hmac-sha1-etm-openssh-com";
          tailf:info
            "hmac-sha1-etm@openssh.com";
        }
        enum "hmac-sha1-96" {
          tailf:info
            "hmac-sha1-96";
        }
        enum "hmac-sha1-96@openssh.com" {
          tailf:code-name "hmac-sha1-96-openssh-com";
          tailf:info
            "hmac-sha1-96@openssh.com";
        }
        enum "hmac-sha2-256" {
          tailf:info
            "hmac-sha2-256";
        }
        enum "hmac-sha2-256-etm@openssh.com" {
          tailf:code-name "hmac-sha2-256-etm-openssh-com";
          tailf:info
            "hmac-sha2-256-etm@openssh.com";
        }
        enum "hmac-sha2-512" {
          tailf:info
            "hmac-sha2-512";
        }
        enum "hmac-sha2-512-etm@openssh.com" {
          tailf:code-name "hmac-sha2-512-etm-openssh-com";
          tailf:info
            "hmac-sha2-512-etm@openssh.com";
        }
        enum "hmac-ripemd160" {
          tailf:info
            "hmac-ripemd160";
        }
        enum "hmac-ripemd160@openssh.com" {
          tailf:code-name "hmac-ripemd160-openssh-com";
          tailf:info
            "hmac-ripemd160@openssh.com";
        }
        enum "hmac-ripemd160-96" {
          tailf:info
            "hmac-ripemd160-96";
        }
        enum "hmac-ripemd160-etm@openssh.com" {
          tailf:code-name "hmac-ripemd160-etm-openssh-com";
          tailf:info
            "hmac-ripemd160-etm@openssh.com";
        }
        enum "AEAD_AES_128_GCM" {
          tailf:code-name "ssh-mac-aead-aes-128-gcm";
          tailf:info
            "AEAD_AES_128_GCM";
        }
        enum "AEAD_AES_256_GCM" {
          tailf:code-name "ssh-mac-aead-aes-256-gcm";
          tailf:info
            "AEAD_AES_256_GCM";
        }
      }
      type string;
    }
  }

  typedef live_ncs_ssh-compression-algorithm {
    type union {
      type enumeration {
        enum "none" {
          tailf:code-name "ssh-compression-none";
          tailf:info
            "No compression";
        }
        enum "zlib" {
          tailf:code-name "ssh-compression-zlib";
          tailf:info
            "ZLIB (LZ77) compression";
        }
        enum "zlib@openssh.com" {
          tailf:code-name "ssh-compression-zlib-openssh-com";
          tailf:info
            "ZLIB (LZ77) compression (OpenSSH version)";
        }
      }
      type string;
    }
  }

  typedef live_ncs_ssh-host-key {
    tailf:info
      "SSH public host key";
    type binary;
    // NCS drop tailf:typepoint
  }

  typedef live_ncs_ssh-private-key-iv {
    tailf:info
      "SSH private user key";
    type tailf:aes-256-cfb-128-encrypted-string;
    // NCS drop tailf:typepoint
  }

  typedef live_ncs_dh-group-size-type {
    type uint32 {
      range "1024 .. 8192";
    }
  }

  typedef ssh-host-key-verification-level {
    description
      "This enumeration is used to specify how strictly the verification of
       SSH host keys is done.";
    type enumeration {
      enum "reject-unknown" {
        tailf:info
          "Reject unknown host keys";
        description
          "With this setting, the SSH host key provided by the device or
           cluster node must already be known.";
      }
      enum "reject-mismatch" {
        tailf:info
          "Reject host keys that do not match the stored key";
        description
          "With this setting, the SSH host key provided by the device or
           cluster node may be unknown, but it must not be different from
           a 'known' key for the same key algorithm.";
      }
      enum "none" {
        tailf:info
          "Accept any host key";
        description
          "With this setting, no SSH host key verification is done - the
           key provided by the device or cluster node may be either unknown
           or different from a 'known' key for the same key algorithm.";
      }
    }
  }

  typedef ssh-key-algorithm {
    type enumeration {
      enum "ssh-dss" {
        tailf:info
          "SSH DSA key";
      }
      enum "ssh-rsa" {
        tailf:info
          "SSH RSA key";
      }
      enum "ssh-ed25519" {
        tailf:info
          "SSH EDDSA (ED25519) key";
      }
      enum "ecdsa-256" {
        tailf:info
          "SSH EcDSA-SHA2-NISTP256 key";
      }
      enum "ecdsa-384" {
        tailf:info
          "SSH EcDSA-SHA2-NISTP384 key";
      }
      enum "ecdsa-521" {
        tailf:info
          "SSH EcDSA-SHA2-NISTP521 key";
      }
      enum "ssh-ed448" {
        tailf:info
          "SSH EDDSA (ED448) key";
      }
    }
  }

  typedef ssh-public-key-algorithm {
    type enumeration {
      enum "ssh-dss" {
        tailf:info
          "SSH DSA key algorithm";
      }
      enum "ssh-rsa" {
        tailf:info
          "SSH RSA key algorithm";
      }
      enum "ssh-ed25519" {
        tailf:info
          "SSH EDDSA (ED25519) key algorithm";
      }
      enum "ecdsa-sha2-nistp256" {
        tailf:info
          "SSH EcDSA-SHA2-NISTP256 key algorithm";
      }
      enum "ecdsa-sha2-nistp384" {
        tailf:info
          "SSH EcDSA-SHA2-NISTP384 key algorithm";
      }
      enum "ecdsa-sha2-nistp521" {
        tailf:info
          "SSH EcDSA-SHA2-NISTP521 key algorithm";
      }
      enum "ssh-ed448" {
        tailf:info
          "SSH EDDSA (ED448) key algorithm";
      }
      enum "rsa-sha2-256" {
        tailf:info
          "SSH RSA-SHA2-256 key algorithm";
      }
      enum "rsa-sha2-512" {
        tailf:info
          "SSH RSA-SHA2-256 key algorithm";
      }
    }
  }

  typedef ssh-kex-algorithm {
    type union {
      type enumeration {
        enum "diffie-hellman-group-exchange-sha1" {
          tailf:info
            "diffie-hellman-group-exchange-sha1";
        }
        enum "diffie-hellman-group-exchange-sha256" {
          tailf:info
            "diffie-hellman-group-exchange-sha256";
        }
        enum "diffie-hellman-group1-sha1" {
          tailf:info
            "diffie-hellman-group1-sha1";
        }
        enum "diffie-hellman-group14-sha1" {
          tailf:info
            "diffie-hellman-group14-sha1";
        }
        enum "diffie-hellman-group14-sha256" {
          tailf:info
            "diffie-hellman-group14-sha256";
        }
        enum "diffie-hellman-group14-sha256@ssh.com" {
          tailf:code-name "diffie-hellman-group14-sha256-ssh-com";
          tailf:info
            "diffie-hellman-group14-sha256@ssh.com";
        }
        enum "diffie-hellman-group15-sha256" {
          tailf:info
            "diffie-hellman-group15-sha256";
        }
        enum "diffie-hellman-group15-sha256@ssh.com" {
          tailf:code-name "diffie-hellman-group15-sha256-ssh-com";
          tailf:info
            "diffie-hellman-group15-sha256@ssh.com";
        }
        enum "diffie-hellman-group15-sha384@ssh.com" {
          tailf:code-name "diffie-hellman-group15-sha384-ssh-com";
          tailf:info
            "diffie-hellman-group15-sha384@ssh.com";
        }
        enum "diffie-hellman-group15-sha512" {
          tailf:info
            "diffie-hellman-group15-sha512";
        }
        enum "diffie-hellman-group16-sha256" {
          tailf:info
            "diffie-hellman-group16-sha256";
        }
        enum "diffie-hellman-group16-sha384@ssh.com" {
          tailf:code-name "diffie-hellman-group16-sha384-ssh-com";
          tailf:info
            "diffie-hellman-group16-sha384@ssh.com";
        }
        enum "diffie-hellman-group16-sha512" {
          tailf:info
            "diffie-hellman-group16-sha512";
        }
        enum "diffie-hellman-group16-sha512@ssh.com" {
          tailf:code-name "diffie-hellman-group16-sha512-ssh-com";
          tailf:info
            "diffie-hellman-group16-sha512@ssh.com";
        }
        enum "diffie-hellman-group17-sha512" {
          tailf:info
            "diffie-hellman-group17-sha512";
        }
        enum "diffie-hellman-group18-sha512" {
          tailf:info
            "diffie-hellman-group18-sha512";
        }
        enum "diffie-hellman-group18-sha512@ssh.com" {
          tailf:code-name "diffie-hellman-group18-sha512-ssh-com";
          tailf:info
            "diffie-hellman-group18-sha512@ssh.com";
        }
        enum "curve448-sha512" {
          tailf:info
            "curve448-sha512";
        }
        enum "curve25519-sha256" {
          tailf:info
            "curve25519-sha256";
        }
        enum "curve25519-sha256@libssh.org" {
          tailf:code-name "curve25519-sha256-libssh-org";
          tailf:info
            "curve25519-sha256@libssh.org";
        }
        enum "curve25519-sha512" {
          tailf:info
            "curve25519-sha512";
        }
        enum "ecdh-sha2-nistp256" {
          tailf:info
            "ecdh-sha2-nistp256";
        }
        enum "ecdh-sha2-nistp384" {
          tailf:info
            "ecdh-sha2-nistp384";
        }
        enum "ecdh-sha2-nistp521" {
          tailf:info
            "ecdh-sha2-nistp521";
        }
        enum "ext-info-c" {
          tailf:info
            "ext-info-c";
        }
      }
      type string;
    }
  }

  typedef ssh-cipher-algorithm {
    type union {
      type enumeration {
        enum "3des-cbc" {
          tailf:info
            "3des-cbc";
        }
        enum "3des-ctr" {
          tailf:info
            "3des-ctr";
        }
        enum "aes128-cbc" {
          tailf:info
            "aes128-cbc";
        }
        enum "aes128-ctr" {
          tailf:info
            "aes128-ctr";
        }
        enum "aes128-gcm@openssh.com" {
          tailf:code-name "aes128-gcm-openssh-com";
          tailf:info
            "aes128-gcm@openssh.com";
        }
        enum "aes192-cbc" {
          tailf:info
            "aes192-cbc";
        }
        enum "aes192-ctr" {
          tailf:info
            "aes192-ctr";
        }
        enum "aes256-cbc" {
          tailf:info
            "aes256-cbc";
        }
        enum "aes256-ctr" {
          tailf:info
            "aes256-ctr";
        }
        enum "aes256-gcm@openssh.com" {
          tailf:code-name "aes256-gcm-openssh-com";
          tailf:info
            "aes256-gcm@openssh.com";
        }
        enum "blowfish-cbc" {
          tailf:info
            "blowfish-cbc";
        }
        enum "blowfish-ctr" {
          tailf:info
            "blowfish-ctr";
        }
        enum "cast128-cbc" {
          tailf:info
            "cast128-cbc";
        }
        enum "cast128-ctr" {
          tailf:info
            "cast128-ctr";
        }
        enum "idea-cbc" {
          tailf:info
            "idea-cbc";
        }
        enum "idea-ctr" {
          tailf:info
            "idea-ctr";
        }
        enum "serpent128-cbc" {
          tailf:info
            "serpent128-cbc";
        }
        enum "serpent128-ctr" {
          tailf:info
            "serpent128-ctr";
        }
        enum "serpent192-cbc" {
          tailf:info
            "serpent192-cbc";
        }
        enum "serpent192-ctr" {
          tailf:info
            "serpent192-ctr";
        }
        enum "serpent256-cbc" {
          tailf:info
            "serpent256-cbc";
        }
        enum "serpent256-ctr" {
          tailf:info
            "serpent256-ctr";
        }
        enum "twofish128-cbc" {
          tailf:info
            "twofish128-cbc";
        }
        enum "twofish128-ctr" {
          tailf:info
            "twofish128-ctr";
        }
        enum "twofish192-cbc" {
          tailf:info
            "twofish192-cbc";
        }
        enum "twofish192-ctr" {
          tailf:info
            "twofish192-ctr";
        }
        enum "twofish256-cbc" {
          tailf:info
            "twofish256-cbc";
        }
        enum "twofish256-ctr" {
          tailf:info
            "twofish256-ctr";
        }
        enum "twofish-cbc" {
          tailf:info
            "twofish-cbc";
        }
        enum "arcfour" {
          tailf:info
            "arcfour";
        }
        enum "arcfour128" {
          tailf:info
            "arcfour128";
        }
        enum "arcfour256" {
          tailf:info
            "arcfour256";
        }
        enum "chacha20-poly1305@openssh.com" {
          tailf:code-name "chacha20-poly1305-openssh-com";
          tailf:info
            "chacha20-poly1305@openssh.com";
        }
        enum "AEAD_AES_128_GCM" {
          tailf:code-name "ssh-cipher-aead-aes-128-gcm";
          tailf:info
            "AEAD_AES_128_GCM";
        }
        enum "AEAD_AES_256_GCM" {
          tailf:code-name "ssh-cipher-aead-aes-256-gcm";
          tailf:info
            "AEAD_AES_256_GCM";
        }
      }
      type string;
    }
  }

  typedef ssh-mac-algorithm {
    type union {
      type enumeration {
        enum "hmac-md5" {
          tailf:info
            "hmac-md5";
        }
        enum "hmac-md5-etm@openssh.com" {
          tailf:code-name "hmac-md5-etm-openssh-com";
          tailf:info
            "hmac-md5-etm@openssh.com";
        }
        enum "hmac-md5-96" {
          tailf:info
            "hmac-md5-96";
        }
        enum "hmac-md5-96-etm@openssh.com" {
          tailf:code-name "hmac-md5-96-etm-openssh-com";
          tailf:info
            "hmac-md5-96-etm@openssh.com";
        }
        enum "hmac-sha1" {
          tailf:info
            "hmac-sha1";
        }
        enum "hmac-sha1-etm@openssh.com" {
          tailf:code-name "hmac-sha1-etm-openssh-com";
          tailf:info
            "hmac-sha1-etm@openssh.com";
        }
        enum "hmac-sha1-96" {
          tailf:info
            "hmac-sha1-96";
        }
        enum "hmac-sha1-96@openssh.com" {
          tailf:code-name "hmac-sha1-96-openssh-com";
          tailf:info
            "hmac-sha1-96@openssh.com";
        }
        enum "hmac-sha2-256" {
          tailf:info
            "hmac-sha2-256";
        }
        enum "hmac-sha2-256-etm@openssh.com" {
          tailf:code-name "hmac-sha2-256-etm-openssh-com";
          tailf:info
            "hmac-sha2-256-etm@openssh.com";
        }
        enum "hmac-sha2-512" {
          tailf:info
            "hmac-sha2-512";
        }
        enum "hmac-sha2-512-etm@openssh.com" {
          tailf:code-name "hmac-sha2-512-etm-openssh-com";
          tailf:info
            "hmac-sha2-512-etm@openssh.com";
        }
        enum "hmac-ripemd160" {
          tailf:info
            "hmac-ripemd160";
        }
        enum "hmac-ripemd160@openssh.com" {
          tailf:code-name "hmac-ripemd160-openssh-com";
          tailf:info
            "hmac-ripemd160@openssh.com";
        }
        enum "hmac-ripemd160-96" {
          tailf:info
            "hmac-ripemd160-96";
        }
        enum "hmac-ripemd160-etm@openssh.com" {
          tailf:code-name "hmac-ripemd160-etm-openssh-com";
          tailf:info
            "hmac-ripemd160-etm@openssh.com";
        }
        enum "AEAD_AES_128_GCM" {
          tailf:code-name "ssh-mac-aead-aes-128-gcm";
          tailf:info
            "AEAD_AES_128_GCM";
        }
        enum "AEAD_AES_256_GCM" {
          tailf:code-name "ssh-mac-aead-aes-256-gcm";
          tailf:info
            "AEAD_AES_256_GCM";
        }
      }
      type string;
    }
  }

  typedef ssh-compression-algorithm {
    type union {
      type enumeration {
        enum "none" {
          tailf:code-name "ssh-compression-none";
          tailf:info
            "No compression";
        }
        enum "zlib" {
          tailf:code-name "ssh-compression-zlib";
          tailf:info
            "ZLIB (LZ77) compression";
        }
        enum "zlib@openssh.com" {
          tailf:code-name "ssh-compression-zlib-openssh-com";
          tailf:info
            "ZLIB (LZ77) compression (OpenSSH version)";
        }
      }
      type string;
    }
  }

  typedef ssh-host-key {
    tailf:info
      "SSH public host key";
    type binary;
    // NCS drop tailf:typepoint
  }

  typedef ssh-private-key-iv {
    tailf:info
      "SSH private user key";
    type tailf:aes-256-cfb-128-encrypted-string;
    // NCS drop tailf:typepoint
  }

  typedef dh-group-size-type {
    type uint32 {
      range "1024 .. 8192";
    }
  }

  grouping ncs_compliance_template_ssh-algorithms {
    leaf-list public-key {
      // NCS patched for predictable order
      ordered-by user;
      description
        "Supported public key algorithms. Only the ones supported by the
         underlying SSH implementation will be used.";
      type ncs_compliance_template_ssh-public-key-algorithm;
    }
    leaf-list kex {
      // NCS patched for predictable order
      ordered-by user;
      description
        "Supported key exchange algorithms. Only the ones supported
         by the underlying SSH implementation will be used.";
      type ncs_compliance_template_ssh-kex-algorithm;
    }
    leaf-list mac {
      // NCS patched for predictable order
      ordered-by user;
      description
        "Supported MAC algorithms. Only the ones supported by the
         underlying SSH implementation will be used.";
      type ncs_compliance_template_ssh-mac-algorithm;
    }
    leaf-list cipher {
      // NCS patched for predictable order
      ordered-by user;
      description
        "Supported cipher algorithms. Only the ones supported by the
         underlying SSH implementation will be used.";
      type ncs_compliance_template_ssh-cipher-algorithm;
    }
    leaf-list compression {
      // NCS patched for predictable order
      ordered-by user;
      description
        "Supported compression algorithms. Only the ones supported by the
         underlying SSH implementation will be used.";
      type ncs_compliance_template_ssh-compression-algorithm;
    }
    container dh-group {
      description
        "Range of allowed group size the client will request during
                  a \"diffie-hellman-group-exchange\". The range will be the
                  intersection of these values and what the server supports";
      leaf min-size {
        // NCS drop must statement
        type ncs_compliance_template_dh-group-size-type;
        description
          "Minimal size of p in bits.";
      }
      leaf preferred-size {
        // NCS drop must statement
        type ncs_compliance_template_dh-group-size-type;
        description
          "Preferred size of p in bits.";
      }
      leaf max-size {
        type ncs_compliance_template_dh-group-size-type;
        description
          "Maximal size of p in bits.";
      }
    }
  }

  grouping ncs_compliance_template_fetch-ssh-host-keys-result {
    description
      "This grouping defines the result of the 'fetch-ssh-host-keys' and
       'fetch-host-keys' actions for one device or cluster node.";

    grouping ssh-host-keys-result {
      description
        "This grouping defines the result of host key retrieval for
         a device, a cluster node, or an additional protocol for the
         live-tree of a device.";
      leaf result {
        description
          "The overall result of the host key retrieval.";
        type string;
      }
      leaf info {
        type string;
        description
          "If present, contains additional information about the result.";
      }
      list fingerprint {
        // NCS patched for predictable order
        ordered-by user;
        description
          "This list gives the key algorithm and fingerprint for each
           retrieved key.";
        key "algorithm";
        leaf algorithm {
          type ncs_compliance_template_ssh-key-algorithm;
        }
        leaf value {
          type string;
        }
      }
    }
    uses ssh-host-keys-result;
    list live-status-protocol {
      // NCS patched for predictable order
      ordered-by user;
      description
        "This list gives the result of key retrieval for additional
         protocols for the live-tree of a device, one entry per protocol.";
      key "name";
      leaf name {
        type string;
        description
          "The name of the protocol, as configured in
           /devices/device/live-status-protocol/name.";
      }
      uses ssh-host-keys-result;
    }
  }

  grouping ncs_compliance_template_ssh-host-keys {
    list host-key {
      // NCS patched for predictable order
      ordered-by user;
      key "algorithm";
      description
        "The list of SSH host keys known by NCS for a device, a cluster
         node, or an additional protocol for the live-tree of a device.
         The list may be populated by the 'fetch-ssh-host-keys' or
         'fetch-host-keys' actions, or by direct configuration.";
      leaf algorithm {
        type ncs_compliance_template_ssh-key-algorithm;
      }
      leaf key-data {
        type ncs_compliance_template_ssh-host-key;
        // NCS drop mandatory statement
        description
          "The binary data for the SSH host key for the given algorithm.
           Besides the direct base64 encoding of the data, the format
           defined by RFC 4716 (produced by 'ssh-keygen -e'), or the
           'native' OpenSSH format, can be used when configuring a key.";
      }
    }
  }

  grouping ncs_compliance_template_ssh-fetch-host-keys;

  grouping ncs_compliance_template_ssh-connection-config {
    container ssh {
      tailf:code-name "ssh_container";
      uses ncs_compliance_template_ssh-host-keys;
      leaf host-key-verification {
        type ncs_compliance_template_ssh-host-key-verification-level;
        description
          "The level of SSH host key verification for a device or cluster
           node. If no value is set, the value of /ssh/host-key-verification
           is used.";
      }
      uses ncs_compliance_template_ssh-fetch-host-keys;
    }
  }

  grouping ncs_compliance_template_public-key-auth {
    container public-key {
      presence "public-key authentication";
      description
        "Parameters for SSH public-key authentication.";
      container private-key {
        choice private-key {
          // NCS drop default statement
          container file {
            description
              "This case will take the private key from a file in the user's
               SSH key directory (determined according to the description of
               /ncs-config/aaa/ssh-pubkey-authentication in the ncs.conf(5)
               manual page). If the key is encrypted, the passphrase for the
               key must be configured via 'passphrase' or 'use-password'.";
            leaf name {
              type string;
              // NCS drop default statement
            }
            choice passphrase-source {
              leaf passphrase {
                type string;
                description
                  "If this leaf exists, its value is used as passphrase
                   for the key if it is encrypted.";
              }
              leaf use-password {
                type empty;
                description
                  "If this leaf exists, the password used by the local user
                   when logging in to NCS is used as passphrase for the key
                   if it is encrypted.";
              }
            }
          }
          leaf name {
            description
              "This case will take the private key identified by 'name' from
               the /ssh/private-key list in the configuration.";
            type string;
          }
        }
      }
    }
  }

  grouping ncs_template_ssh-algorithms {
    leaf-list public-key {
      // NCS patched for predictable order
      ordered-by user;
      description
        "Supported public key algorithms. Only the ones supported by the
         underlying SSH implementation will be used.";
      type ncs_template_ssh-public-key-algorithm;
    }
    leaf-list kex {
      // NCS patched for predictable order
      ordered-by user;
      description
        "Supported key exchange algorithms. Only the ones supported
         by the underlying SSH implementation will be used.";
      type ncs_template_ssh-kex-algorithm;
    }
    leaf-list mac {
      // NCS patched for predictable order
      ordered-by user;
      description
        "Supported MAC algorithms. Only the ones supported by the
         underlying SSH implementation will be used.";
      type ncs_template_ssh-mac-algorithm;
    }
    leaf-list cipher {
      // NCS patched for predictable order
      ordered-by user;
      description
        "Supported cipher algorithms. Only the ones supported by the
         underlying SSH implementation will be used.";
      type ncs_template_ssh-cipher-algorithm;
    }
    leaf-list compression {
      // NCS patched for predictable order
      ordered-by user;
      description
        "Supported compression algorithms. Only the ones supported by the
         underlying SSH implementation will be used.";
      type ncs_template_ssh-compression-algorithm;
    }
    container dh-group {
      description
        "Range of allowed group size the client will request during
                  a \"diffie-hellman-group-exchange\". The range will be the
                  intersection of these values and what the server supports";
      leaf min-size {
        // NCS drop must statement
        type ncs_template_dh-group-size-type;
        description
          "Minimal size of p in bits.";
      }
      leaf preferred-size {
        // NCS drop must statement
        type ncs_template_dh-group-size-type;
        description
          "Preferred size of p in bits.";
      }
      leaf max-size {
        type ncs_template_dh-group-size-type;
        description
          "Maximal size of p in bits.";
      }
    }
  }

  grouping ncs_template_fetch-ssh-host-keys-result {
    description
      "This grouping defines the result of the 'fetch-ssh-host-keys' and
       'fetch-host-keys' actions for one device or cluster node.";

    grouping ssh-host-keys-result {
      description
        "This grouping defines the result of host key retrieval for
         a device, a cluster node, or an additional protocol for the
         live-tree of a device.";
      leaf result {
        description
          "The overall result of the host key retrieval.";
        type string;
      }
      leaf info {
        type string;
        description
          "If present, contains additional information about the result.";
      }
      list fingerprint {
        // NCS patched for predictable order
        ordered-by user;
        description
          "This list gives the key algorithm and fingerprint for each
           retrieved key.";
        key "algorithm";
        leaf algorithm {
          type ncs_template_ssh-key-algorithm;
        }
        leaf value {
          type string;
        }
      }
    }
    uses ssh-host-keys-result;
    list live-status-protocol {
      // NCS patched for predictable order
      ordered-by user;
      description
        "This list gives the result of key retrieval for additional
         protocols for the live-tree of a device, one entry per protocol.";
      key "name";
      leaf name {
        type string;
        description
          "The name of the protocol, as configured in
           /devices/device/live-status-protocol/name.";
      }
      uses ssh-host-keys-result;
    }
  }

  grouping ncs_template_ssh-host-keys {
    list host-key {
      // NCS patched for predictable order
      ordered-by user;
      key "algorithm";
      description
        "The list of SSH host keys known by NCS for a device, a cluster
         node, or an additional protocol for the live-tree of a device.
         The list may be populated by the 'fetch-ssh-host-keys' or
         'fetch-host-keys' actions, or by direct configuration.";
      leaf algorithm {
        type ncs_template_ssh-key-algorithm;
      }
      leaf key-data {
        type ncs_template_ssh-host-key;
        // NCS drop mandatory statement
        description
          "The binary data for the SSH host key for the given algorithm.
           Besides the direct base64 encoding of the data, the format
           defined by RFC 4716 (produced by 'ssh-keygen -e'), or the
           'native' OpenSSH format, can be used when configuring a key.";
      }
    }
  }

  grouping ncs_template_ssh-fetch-host-keys;

  grouping ncs_template_ssh-connection-config {
    container ssh {
      tailf:code-name "ssh_container";
      uses ncs_template_ssh-host-keys;
      leaf host-key-verification {
        type ncs_template_ssh-host-key-verification-level;
        description
          "The level of SSH host key verification for a device or cluster
           node. If no value is set, the value of /ssh/host-key-verification
           is used.";
      }
      uses ncs_template_ssh-fetch-host-keys;
    }
  }

  grouping ncs_template_public-key-auth {
    container public-key {
      presence "public-key authentication";
      description
        "Parameters for SSH public-key authentication.";
      container private-key {
        choice private-key {
          // NCS drop default statement
          container file {
            description
              "This case will take the private key from a file in the user's
               SSH key directory (determined according to the description of
               /ncs-config/aaa/ssh-pubkey-authentication in the ncs.conf(5)
               manual page). If the key is encrypted, the passphrase for the
               key must be configured via 'passphrase' or 'use-password'.";
            leaf name {
              type string;
              // NCS drop default statement
            }
            choice passphrase-source {
              leaf passphrase {
                type string;
                description
                  "If this leaf exists, its value is used as passphrase
                   for the key if it is encrypted.";
              }
              leaf use-password {
                type empty;
                description
                  "If this leaf exists, the password used by the local user
                   when logging in to NCS is used as passphrase for the key
                   if it is encrypted.";
              }
            }
          }
          leaf name {
            description
              "This case will take the private key identified by 'name' from
               the /ssh/private-key list in the configuration.";
            type string;
          }
        }
      }
    }
  }

  grouping ncs_rpc_notif_ssh-algorithms {
    leaf-list public-key {
      description
        "Supported public key algorithms. Only the ones supported by the
         underlying SSH implementation will be used.";
      type ncs_rpc_notif_ssh-public-key-algorithm;
      ordered-by user;
    }
    leaf-list kex {
      description
        "Supported key exchange algorithms. Only the ones supported
         by the underlying SSH implementation will be used.";
      ordered-by user;
      type ncs_rpc_notif_ssh-kex-algorithm;
    }
    leaf-list mac {
      description
        "Supported MAC algorithms. Only the ones supported by the
         underlying SSH implementation will be used.";
      ordered-by user;
      type ncs_rpc_notif_ssh-mac-algorithm;
    }
    leaf-list cipher {
      description
        "Supported cipher algorithms. Only the ones supported by the
         underlying SSH implementation will be used.";
      ordered-by user;
      type ncs_rpc_notif_ssh-cipher-algorithm;
    }
    leaf-list compression {
      description
        "Supported compression algorithms. Only the ones supported by the
         underlying SSH implementation will be used.";
      ordered-by user;
      type ncs_rpc_notif_ssh-compression-algorithm;
    }
    container dh-group {
      description
        "Range of allowed group size the client will request during
                  a \"diffie-hellman-group-exchange\". The range will be the
                  intersection of these values and what the server supports";
      leaf min-size {
        must '. <= ../max-size' {
          tailf:xpath-root 3;
        }
        type ncs_rpc_notif_dh-group-size-type;
        description
          "Minimal size of p in bits.";
      }
      leaf preferred-size {
        must '. <= ../max-size and . >= ../min-size' {
          tailf:xpath-root 3;
        }
        type ncs_rpc_notif_dh-group-size-type;
        description
          "Preferred size of p in bits.";
      }
      leaf max-size {
        type ncs_rpc_notif_dh-group-size-type;
        description
          "Maximal size of p in bits.";
      }
    }
  }

  grouping ncs_rpc_notif_fetch-ssh-host-keys-result {
    description
      "This grouping defines the result of the 'fetch-ssh-host-keys' and
       'fetch-host-keys' actions for one device or cluster node.";

    grouping ssh-host-keys-result {
      description
        "This grouping defines the result of host key retrieval for
         a device, a cluster node, or an additional protocol for the
         live-tree of a device.";
      leaf result {
        description
          "The overall result of the host key retrieval.";
        type enumeration {
          enum "failed" {
            description
              "The key retrieval failed, e.g. due to failure to connect
               to the device or cluster node.";
            tailf:code-name "hostkey_failed";
          }
          enum "unchanged" {
            description
              "The key retrieval succeeded, and the keys were the same
               as those already known.";
          }
          enum "updated" {
            description
              "The key retrieval succeeded, and the keys were not the same
               as those already known - i.e. there was at least one new or
               changed key. The updated keys were committed";
          }
          enum "updated-uncommitted" {
            description
              "The key retrieval succeeded, and the keys were not the same
               as those already known - i.e. there was at least one new or
               changed key. The updated keys were not committed, only stored
               in the current transaction, since the device or cluster node
               entry the keys pertain to was not committed (i.e. it only
               exists in the current transaction). The keys will be
               committed when the user commits the transaction.";
          }
          enum "not-available" {
            description
              "Key retrieval was not attempted due to not being applicable for
               the device type or additional live-tree protocol (e.g. CLI
               access via telnet rather than SSH).";
          }
        }
      }
      leaf info {
        type string;
        description
          "If present, contains additional information about the result.";
      }
      list fingerprint {
        description
          "This list gives the key algorithm and fingerprint for each
           retrieved key.";
        key "algorithm";
        leaf algorithm {
          type ncs_rpc_notif_ssh-key-algorithm;
        }
        leaf value {
          type yang:hex-string;
        }
      }
    }
    uses ssh-host-keys-result;
    list live-status-protocol {
      description
        "This list gives the result of key retrieval for additional
         protocols for the live-tree of a device, one entry per protocol.";
      key "name";
      leaf name {
        type string;
        description
          "The name of the protocol, as configured in
           /devices/device/live-status-protocol/name.";
      }
      uses ssh-host-keys-result;
    }
  }

  grouping ncs_rpc_notif_ssh-host-keys {
    list host-key {
      tailf:info
        "Known SSH host keys";
      key "algorithm";
      description
        "The list of SSH host keys known by NCS for a device, a cluster
         node, or an additional protocol for the live-tree of a device.
         The list may be populated by the 'fetch-ssh-host-keys' or
         'fetch-host-keys' actions, or by direct configuration.";
      leaf algorithm {
        type ncs_rpc_notif_ssh-key-algorithm;
        tailf:cli-allow-range;
      }
      leaf key-data {
        type ncs_rpc_notif_ssh-host-key;
        mandatory true;
        description
          "The binary data for the SSH host key for the given algorithm.
           Besides the direct base64 encoding of the data, the format
           defined by RFC 4716 (produced by 'ssh-keygen -e'), or the
           'native' OpenSSH format, can be used when configuring a key.";
        tailf:cli-multi-line-prompt;
        // NCS drop tailf:validate
      }
      // NCS drop tailf:action
    }
  }

  grouping ncs_rpc_notif_ssh-fetch-host-keys {
    // NCS drop tailf:action
  }

  grouping ncs_rpc_notif_ssh-connection-config {
    container ssh {
      tailf:info
        "SSH connection configuration";
      tailf:code-name "ssh_container";
      uses ncs_rpc_notif_ssh-host-keys;
      leaf host-key-verification {
        tailf:info
          "Level of host key verification";
        type ncs_rpc_notif_ssh-host-key-verification-level;
        // NCS dropped default_ref using absolute path 
        description
          "The level of SSH host key verification for a device or cluster
           node. If no value is set, the value of /ssh/host-key-verification
           is used.";
      }
      uses ncs_rpc_notif_ssh-fetch-host-keys;
    }
  }

  grouping ncs_rpc_notif_public-key-auth {
    container public-key {
      presence "public-key authentication";
      tailf:info
        "Use public-key authentication";
      description
        "Parameters for SSH public-key authentication.";
      container private-key {
        tailf:info
          "Specify which private key to use for authentication";
        choice private-key {
          default "file";
          container file {
            tailf:info
              "Use private key file in local user's key directory";
            description
              "This case will take the private key from a file in the user's
               SSH key directory (determined according to the description of
               /ncs-config/aaa/ssh-pubkey-authentication in the ncs.conf(5)
               manual page). If the key is encrypted, the passphrase for the
               key must be configured via 'passphrase' or 'use-password'.";
            leaf name {
              tailf:info
                "Name of private key file";
              type string;
              default "id_dsa";
            }
            choice passphrase-source {
              leaf passphrase {
                tailf:info
                  "Passphrase for private key";
                type tailf:aes-256-cfb-128-encrypted-string;
                tailf:suppress-echo true;
                description
                  "If this leaf exists, its value is used as passphrase
                   for the key if it is encrypted.";
              }
              leaf use-password {
                tailf:info
                  "Use local user's password as passphrase";
                type empty;
                description
                  "If this leaf exists, the password used by the local user
                   when logging in to NCS is used as passphrase for the key
                   if it is encrypted.";
              }
            }
          }
          leaf name {
            tailf:info
              "Name of private key configured in /ssh/private-key";
            description
              "This case will take the private key identified by 'name' from
               the /ssh/private-key list in the configuration.";
            type string;
          }
        }
      }
    }
  }

  grouping live_ncs_ssh-algorithms {
    leaf-list public-key {
      description
        "Supported public key algorithms. Only the ones supported by the
         underlying SSH implementation will be used.";
      type live_ncs_ssh-public-key-algorithm;
      ordered-by user;
    }
    leaf-list kex {
      description
        "Supported key exchange algorithms. Only the ones supported
         by the underlying SSH implementation will be used.";
      ordered-by user;
      type live_ncs_ssh-kex-algorithm;
    }
    leaf-list mac {
      description
        "Supported MAC algorithms. Only the ones supported by the
         underlying SSH implementation will be used.";
      ordered-by user;
      type live_ncs_ssh-mac-algorithm;
    }
    leaf-list cipher {
      description
        "Supported cipher algorithms. Only the ones supported by the
         underlying SSH implementation will be used.";
      ordered-by user;
      type live_ncs_ssh-cipher-algorithm;
    }
    leaf-list compression {
      description
        "Supported compression algorithms. Only the ones supported by the
         underlying SSH implementation will be used.";
      ordered-by user;
      type live_ncs_ssh-compression-algorithm;
    }
    container dh-group {
      description
        "Range of allowed group size the client will request during
                  a \"diffie-hellman-group-exchange\". The range will be the
                  intersection of these values and what the server supports";
      leaf min-size {
        // NCS drop must statement
        type live_ncs_dh-group-size-type;
        description
          "Minimal size of p in bits.";
      }
      leaf preferred-size {
        // NCS drop must statement
        type live_ncs_dh-group-size-type;
        description
          "Preferred size of p in bits.";
      }
      leaf max-size {
        type live_ncs_dh-group-size-type;
        description
          "Maximal size of p in bits.";
      }
    }
  }

  grouping live_ncs_fetch-ssh-host-keys-result {
    description
      "This grouping defines the result of the 'fetch-ssh-host-keys' and
       'fetch-host-keys' actions for one device or cluster node.";

    grouping ssh-host-keys-result {
      description
        "This grouping defines the result of host key retrieval for
         a device, a cluster node, or an additional protocol for the
         live-tree of a device.";
      leaf result {
        description
          "The overall result of the host key retrieval.";
        type enumeration {
          enum "failed" {
            description
              "The key retrieval failed, e.g. due to failure to connect
               to the device or cluster node.";
            tailf:code-name "hostkey_failed";
          }
          enum "unchanged" {
            description
              "The key retrieval succeeded, and the keys were the same
               as those already known.";
          }
          enum "updated" {
            description
              "The key retrieval succeeded, and the keys were not the same
               as those already known - i.e. there was at least one new or
               changed key. The updated keys were committed";
          }
          enum "updated-uncommitted" {
            description
              "The key retrieval succeeded, and the keys were not the same
               as those already known - i.e. there was at least one new or
               changed key. The updated keys were not committed, only stored
               in the current transaction, since the device or cluster node
               entry the keys pertain to was not committed (i.e. it only
               exists in the current transaction). The keys will be
               committed when the user commits the transaction.";
          }
          enum "not-available" {
            description
              "Key retrieval was not attempted due to not being applicable for
               the device type or additional live-tree protocol (e.g. CLI
               access via telnet rather than SSH).";
          }
        }
      }
      leaf info {
        type string;
        description
          "If present, contains additional information about the result.";
      }
      list fingerprint {
        description
          "This list gives the key algorithm and fingerprint for each
           retrieved key.";
        key "algorithm";
        leaf algorithm {
          type live_ncs_ssh-key-algorithm;
        }
        leaf value {
          type yang:hex-string;
        }
      }
    }
    uses ssh-host-keys-result;
    list live-status-protocol {
      description
        "This list gives the result of key retrieval for additional
         protocols for the live-tree of a device, one entry per protocol.";
      key "name";
      leaf name {
        type string;
        description
          "The name of the protocol, as configured in
           /devices/device/live-status-protocol/name.";
      }
      uses ssh-host-keys-result;
    }
  }

  grouping live_ncs_ssh-host-keys {
    list host-key {
      tailf:info
        "Known SSH host keys";
      key "algorithm";
      description
        "The list of SSH host keys known by NCS for a device, a cluster
         node, or an additional protocol for the live-tree of a device.
         The list may be populated by the 'fetch-ssh-host-keys' or
         'fetch-host-keys' actions, or by direct configuration.";
      leaf algorithm {
        type live_ncs_ssh-key-algorithm;
        // NCS drop tailf:cli-allow-range
      }
      leaf key-data {
        type live_ncs_ssh-host-key;
        // NCS drop mandatory statement
        description
          "The binary data for the SSH host key for the given algorithm.
           Besides the direct base64 encoding of the data, the format
           defined by RFC 4716 (produced by 'ssh-keygen -e'), or the
           'native' OpenSSH format, can be used when configuring a key.";
        // NCS drop tailf:cli-multi-line-prompt
        // NCS drop tailf:validate
      }
      tailf:action show-fingerprint {
        tailf:actionpoint ncsproxy {
          tailf:internal;
        }
        tailf:info
          "Show the fingerprint for the key";
        // NCS drop tailf:actionpoint
        output {
          leaf value {
            type yang:hex-string;
          }
        }
      }
    }
  }

  grouping live_ncs_ssh-fetch-host-keys {
    tailf:action fetch-host-keys {
      tailf:actionpoint ncsproxy {
        tailf:internal;
      }
      tailf:info
        "Retrieve host keys from remote";
      description
        "Retrieve the SSH host keys from the device or remote cluster
         node and store them in the 'host-key' list. The keys will be
         committed by the action when possible, i.e. when the device or
         cluster node entry is already committed. Otherwise the keys
         are stored in the current transaction, and committed only when
         the user commits the transaction.";
      // NCS drop tailf:actionpoint
      output {
        uses live_ncs_fetch-ssh-host-keys-result;
      }
    }
  }

  grouping live_ncs_ssh-connection-config {
    container ssh {
      tailf:info
        "SSH connection configuration";
      tailf:code-name "ssh_container";
      uses live_ncs_ssh-host-keys;
      leaf host-key-verification {
        tailf:info
          "Level of host key verification";
        type live_ncs_ssh-host-key-verification-level;
        // NCS dropped default_ref using absolute path 
        description
          "The level of SSH host key verification for a device or cluster
           node. If no value is set, the value of /ssh/host-key-verification
           is used.";
      }
      uses live_ncs_ssh-fetch-host-keys;
    }
  }

  grouping live_ncs_public-key-auth {
    container public-key {
      presence "public-key authentication";
      tailf:info
        "Use public-key authentication";
      description
        "Parameters for SSH public-key authentication.";
      container private-key {
        tailf:info
          "Specify which private key to use for authentication";
        choice private-key {
          // NCS drop default statement
          container file {
            tailf:info
              "Use private key file in local user's key directory";
            description
              "This case will take the private key from a file in the user's
               SSH key directory (determined according to the description of
               /ncs-config/aaa/ssh-pubkey-authentication in the ncs.conf(5)
               manual page). If the key is encrypted, the passphrase for the
               key must be configured via 'passphrase' or 'use-password'.";
            leaf name {
              tailf:info
                "Name of private key file";
              type string;
              // NCS drop default statement
            }
            choice passphrase-source {
              leaf passphrase {
                tailf:info
                  "Passphrase for private key";
                type tailf:aes-256-cfb-128-encrypted-string;
                tailf:suppress-echo true;
                description
                  "If this leaf exists, its value is used as passphrase
                   for the key if it is encrypted.";
              }
              leaf use-password {
                tailf:info
                  "Use local user's password as passphrase";
                type empty;
                description
                  "If this leaf exists, the password used by the local user
                   when logging in to NCS is used as passphrase for the key
                   if it is encrypted.";
              }
            }
          }
          leaf name {
            tailf:info
              "Name of private key configured in /ssh/private-key";
            description
              "This case will take the private key identified by 'name' from
               the /ssh/private-key list in the configuration.";
            type leafref {
              path "/ncs-internal:devices/ncs-internal:device/ncs-internal:live-status/ssh/private-key/name" {
                tailf:xpath-root 3;
              }
            }
          }
        }
      }
    }
  }

  grouping ssh-algorithms {
    leaf-list public-key {
      description
        "Supported public key algorithms. Only the ones supported by the
         underlying SSH implementation will be used.";
      type ssh-public-key-algorithm;
      ordered-by user;
    }
    leaf-list kex {
      description
        "Supported key exchange algorithms. Only the ones supported
         by the underlying SSH implementation will be used.";
      ordered-by user;
      type ssh-kex-algorithm;
    }
    leaf-list mac {
      description
        "Supported MAC algorithms. Only the ones supported by the
         underlying SSH implementation will be used.";
      ordered-by user;
      type ssh-mac-algorithm;
    }
    leaf-list cipher {
      description
        "Supported cipher algorithms. Only the ones supported by the
         underlying SSH implementation will be used.";
      ordered-by user;
      type ssh-cipher-algorithm;
    }
    leaf-list compression {
      description
        "Supported compression algorithms. Only the ones supported by the
         underlying SSH implementation will be used.";
      ordered-by user;
      type ssh-compression-algorithm;
    }
    container dh-group {
      description
        "Range of allowed group size the client will request during
                  a \"diffie-hellman-group-exchange\". The range will be the
                  intersection of these values and what the server supports";
      leaf min-size {
        must '. <= ../max-size' {
          tailf:xpath-root 3;
        }
        type dh-group-size-type;
        description
          "Minimal size of p in bits.";
      }
      leaf preferred-size {
        must '. <= ../max-size and . >= ../min-size' {
          tailf:xpath-root 3;
        }
        type dh-group-size-type;
        description
          "Preferred size of p in bits.";
      }
      leaf max-size {
        type dh-group-size-type;
        description
          "Maximal size of p in bits.";
      }
    }
  }

  grouping fetch-ssh-host-keys-result {
    description
      "This grouping defines the result of the 'fetch-ssh-host-keys' and
       'fetch-host-keys' actions for one device or cluster node.";

    grouping ssh-host-keys-result {
      description
        "This grouping defines the result of host key retrieval for
         a device, a cluster node, or an additional protocol for the
         live-tree of a device.";
      leaf result {
        description
          "The overall result of the host key retrieval.";
        type enumeration {
          enum "failed" {
            description
              "The key retrieval failed, e.g. due to failure to connect
               to the device or cluster node.";
            tailf:code-name "hostkey_failed";
          }
          enum "unchanged" {
            description
              "The key retrieval succeeded, and the keys were the same
               as those already known.";
          }
          enum "updated" {
            description
              "The key retrieval succeeded, and the keys were not the same
               as those already known - i.e. there was at least one new or
               changed key. The updated keys were committed";
          }
          enum "updated-uncommitted" {
            description
              "The key retrieval succeeded, and the keys were not the same
               as those already known - i.e. there was at least one new or
               changed key. The updated keys were not committed, only stored
               in the current transaction, since the device or cluster node
               entry the keys pertain to was not committed (i.e. it only
               exists in the current transaction). The keys will be
               committed when the user commits the transaction.";
          }
          enum "not-available" {
            description
              "Key retrieval was not attempted due to not being applicable for
               the device type or additional live-tree protocol (e.g. CLI
               access via telnet rather than SSH).";
          }
        }
      }
      leaf info {
        type string;
        description
          "If present, contains additional information about the result.";
      }
      list fingerprint {
        description
          "This list gives the key algorithm and fingerprint for each
           retrieved key.";
        key "algorithm";
        leaf algorithm {
          type ssh-key-algorithm;
        }
        leaf value {
          type yang:hex-string;
        }
      }
    }
    uses ssh-host-keys-result;
    list live-status-protocol {
      description
        "This list gives the result of key retrieval for additional
         protocols for the live-tree of a device, one entry per protocol.";
      key "name";
      leaf name {
        type string;
        description
          "The name of the protocol, as configured in
           /devices/device/live-status-protocol/name.";
      }
      uses ssh-host-keys-result;
    }
  }

  grouping ssh-host-keys {
    list host-key {
      tailf:info
        "Known SSH host keys";
      key "algorithm";
      description
        "The list of SSH host keys known by NCS for a device, a cluster
         node, or an additional protocol for the live-tree of a device.
         The list may be populated by the 'fetch-ssh-host-keys' or
         'fetch-host-keys' actions, or by direct configuration.";
      leaf algorithm {
        type ssh-key-algorithm;
        tailf:cli-allow-range;
      }
      leaf key-data {
        type ssh-host-key;
        mandatory true;
        description
          "The binary data for the SSH host key for the given algorithm.
           Besides the direct base64 encoding of the data, the format
           defined by RFC 4716 (produced by 'ssh-keygen -e'), or the
           'native' OpenSSH format, can be used when configuring a key.";
        tailf:cli-multi-line-prompt;
        // NCS drop tailf:validate
      }
      tailf:action show-fingerprint {
        tailf:actionpoint ncsproxy {
          tailf:internal;
        }
        tailf:info
          "Show the fingerprint for the key";
        // NCS drop tailf:actionpoint
        output {
          leaf value {
            type yang:hex-string;
          }
        }
      }
    }
  }

  grouping ssh-fetch-host-keys {
    tailf:action fetch-host-keys {
      tailf:actionpoint ncsproxy {
        tailf:internal;
      }
      tailf:info
        "Retrieve host keys from remote";
      description
        "Retrieve the SSH host keys from the device or remote cluster
         node and store them in the 'host-key' list. The keys will be
         committed by the action when possible, i.e. when the device or
         cluster node entry is already committed. Otherwise the keys
         are stored in the current transaction, and committed only when
         the user commits the transaction.";
      // NCS drop tailf:actionpoint
      output {
        uses fetch-ssh-host-keys-result;
      }
    }
  }

  grouping ssh-connection-config {
    container ssh {
      tailf:info
        "SSH connection configuration";
      tailf:code-name "ssh_container";
      uses ssh-host-keys;
      leaf host-key-verification {
        tailf:info
          "Level of host key verification";
        type ssh-host-key-verification-level;
        // NCS dropped default_ref using absolute path 
        description
          "The level of SSH host key verification for a device or cluster
           node. If no value is set, the value of /ssh/host-key-verification
           is used.";
      }
      uses ssh-fetch-host-keys;
    }
  }

  grouping public-key-auth {
    container public-key {
      presence "public-key authentication";
      tailf:info
        "Use public-key authentication";
      description
        "Parameters for SSH public-key authentication.";
      container private-key {
        tailf:info
          "Specify which private key to use for authentication";
        choice private-key {
          default "file";
          container file {
            tailf:info
              "Use private key file in local user's key directory";
            description
              "This case will take the private key from a file in the user's
               SSH key directory (determined according to the description of
               /ncs-config/aaa/ssh-pubkey-authentication in the ncs.conf(5)
               manual page). If the key is encrypted, the passphrase for the
               key must be configured via 'passphrase' or 'use-password'.";
            leaf name {
              tailf:info
                "Name of private key file";
              type string;
              default "id_dsa";
            }
            choice passphrase-source {
              leaf passphrase {
                tailf:ned-ignore-compare-config;
                tailf:info
                  "Passphrase for private key";
                type tailf:aes-256-cfb-128-encrypted-string;
                tailf:suppress-echo true;
                description
                  "If this leaf exists, its value is used as passphrase
                   for the key if it is encrypted.";
              }
              leaf use-password {
                tailf:info
                  "Use local user's password as passphrase";
                type empty;
                description
                  "If this leaf exists, the password used by the local user
                   when logging in to NCS is used as passphrase for the key
                   if it is encrypted.";
              }
            }
          }
          leaf name {
            tailf:info
              "Name of private key configured in /ssh/private-key";
            description
              "This case will take the private key identified by 'name' from
               the /ssh/private-key list in the configuration.";
            type leafref {
              path "/ncs-internal:devices/ncs-internal:device/ncs-internal:config/ssh/private-key/name" {
                tailf:xpath-root 3;
              }
            }
          }
        }
      }
    }
  }

  augment "/ncs-internal:devices/ncs-internal:device/ncs-internal:config" {
    container ssh {
      tailf:ncs-device-type "netconf";
      tailf:display-when "not(../../ncs-internal:module) or ../../ncs-internal:module[ncs-internal:name='tailf-ncs']";
      tailf:info
        "Global SSH connection configuration";
      tailf:code-name "ssh_container";
      leaf host-key-verification {
        tailf:info
          "Level of host key verification";
        type ssh-host-key-verification-level;
        default "reject-unknown";
        description
          "The level of SSH host key verification for a devices and cluster
           nodes that do not have a level set in the device/node-specific
           SSH connection configuration.";
      }
      list private-key {
        tailf:info
          "Configured private keys";
        description
          "This list holds named private keys that can be used for SSH
           public-key authentication towards a device or cluster node.";
        key "name";
        leaf name {
          tailf:info
            "Name of key";
          type string;
          description
            "An arbitrary name for the key, used as reference when configuring
             public-key authentication.";
        }
        leaf key-data {
          type ssh-private-key-iv;
          mandatory true;
          tailf:cli-multi-line-prompt;
          // NCS drop tailf:validate
          description
            "The binary data for the private key, in one of several possible
             PEM formats. Either in PKCS#1 format (text starting with
             '-----BEGIN DSA PRIVATE KEY-----' or
             '-----BEGIN RSA PRIVATE KEY-----') or in PKCS#8 format (text
             starting with '-----BEGIN PRIVATE KEY-----' or
             '-----BEGIN ENCRYPTED PRIVATE KEY-----') or in OpenSSH format
             (text starting with '-----BEGIN OPENSSH PRIVATE KEY-----').
             If the key is encrypted, the passphrase for the key must be
             configured via 'passphrase'.";
        }
        leaf passphrase {
          tailf:ned-ignore-compare-config;
          tailf:info
            "Passphrase for key";
          type tailf:aes-256-cfb-128-encrypted-string;
          tailf:suppress-echo true;
          description
            "The value of this leaf is used as passphrase for the key if
             it is encrypted.";
        }
      }
    }
  }
  augment "/ncs-internal:devices/ncs-internal:device/ncs-internal:live-status" {
    container ssh {
      tailf:ncs-device-type "netconf";
      tailf:display-when "not(../../ncs-internal:module) or ../../ncs-internal:module[ncs-internal:name='tailf-ncs'] or (../../ncs-internal:live-status-protocol[not(ncs-internal:capability)]) or (../../ncs-internal:live-status-protocol/ncs-internal:capability/ncs-internal:module[.='tailf-ncs'])";
      tailf:info
        "Global SSH connection configuration";
      tailf:code-name "ssh_container";
      leaf host-key-verification {
        tailf:info
          "Level of host key verification";
        type live_ncs_ssh-host-key-verification-level;
        // NCS drop default statement
        description
          "The level of SSH host key verification for a devices and cluster
           nodes that do not have a level set in the device/node-specific
           SSH connection configuration.";
      }
      list private-key {
        tailf:info
          "Configured private keys";
        description
          "This list holds named private keys that can be used for SSH
           public-key authentication towards a device or cluster node.";
        key "name";
        leaf name {
          tailf:info
            "Name of key";
          type string;
          description
            "An arbitrary name for the key, used as reference when configuring
             public-key authentication.";
        }
        leaf key-data {
          type live_ncs_ssh-private-key-iv;
          // NCS drop mandatory statement
          // NCS drop tailf:cli-multi-line-prompt
          // NCS drop tailf:validate
          description
            "The binary data for the private key, in one of several possible
             PEM formats. Either in PKCS#1 format (text starting with
             '-----BEGIN DSA PRIVATE KEY-----' or
             '-----BEGIN RSA PRIVATE KEY-----') or in PKCS#8 format (text
             starting with '-----BEGIN PRIVATE KEY-----' or
             '-----BEGIN ENCRYPTED PRIVATE KEY-----') or in OpenSSH format
             (text starting with '-----BEGIN OPENSSH PRIVATE KEY-----').
             If the key is encrypted, the passphrase for the key must be
             configured via 'passphrase'.";
        }
        leaf passphrase {
          tailf:info
            "Passphrase for key";
          type tailf:aes-256-cfb-128-encrypted-string;
          tailf:suppress-echo true;
          description
            "The value of this leaf is used as passphrase for the key if
             it is encrypted.";
        }
      }
    }
  }
  augment "/ncs-internal:devices/ncs-internal:template/ncs-internal:ned-id/ncs-internal:config" {
    container ssh {
      tailf:code-name "ssh_container";
      leaf host-key-verification {
        type ncs_template_ssh-host-key-verification-level;
        // NCS drop default statement
        description
          "The level of SSH host key verification for a devices and cluster
           nodes that do not have a level set in the device/node-specific
           SSH connection configuration.";
      }
      list private-key {
        // NCS patched for predictable order
        ordered-by user;
        description
          "This list holds named private keys that can be used for SSH
           public-key authentication towards a device or cluster node.";
        key "name";
        leaf name {
          type string;
          description
            "An arbitrary name for the key, used as reference when configuring
             public-key authentication.";
        }
        leaf key-data {
          type ncs_template_ssh-private-key-iv;
          // NCS drop mandatory statement
          description
            "The binary data for the private key, in one of several possible
             PEM formats. Either in PKCS#1 format (text starting with
             '-----BEGIN DSA PRIVATE KEY-----' or
             '-----BEGIN RSA PRIVATE KEY-----') or in PKCS#8 format (text
             starting with '-----BEGIN PRIVATE KEY-----' or
             '-----BEGIN ENCRYPTED PRIVATE KEY-----') or in OpenSSH format
             (text starting with '-----BEGIN OPENSSH PRIVATE KEY-----').
             If the key is encrypted, the passphrase for the key must be
             configured via 'passphrase'.";
        }
        leaf passphrase {
          type string;
          description
            "The value of this leaf is used as passphrase for the key if
             it is encrypted.";
        }
      }
    }
  }
  augment "/ncs-internal:compliance/ncs-internal:template/ncs-internal:ned-id/ncs-internal:config" {
    container ssh {
      tailf:code-name "ssh_container";
      leaf host-key-verification {
        type ncs_compliance_template_ssh-host-key-verification-level;
        // NCS drop default statement
        description
          "The level of SSH host key verification for a devices and cluster
           nodes that do not have a level set in the device/node-specific
           SSH connection configuration.";
      }
      list private-key {
        // NCS patched for predictable order
        ordered-by user;
        description
          "This list holds named private keys that can be used for SSH
           public-key authentication towards a device or cluster node.";
        key "name";
        leaf name {
          type string;
          description
            "An arbitrary name for the key, used as reference when configuring
             public-key authentication.";
        }
        leaf key-data {
          type ncs_compliance_template_ssh-private-key-iv;
          // NCS drop mandatory statement
          description
            "The binary data for the private key, in one of several possible
             PEM formats. Either in PKCS#1 format (text starting with
             '-----BEGIN DSA PRIVATE KEY-----' or
             '-----BEGIN RSA PRIVATE KEY-----') or in PKCS#8 format (text
             starting with '-----BEGIN PRIVATE KEY-----' or
             '-----BEGIN ENCRYPTED PRIVATE KEY-----') or in OpenSSH format
             (text starting with '-----BEGIN OPENSSH PRIVATE KEY-----').
             If the key is encrypted, the passphrase for the key must be
             configured via 'passphrase'.";
        }
        leaf passphrase {
          type string;
          description
            "The value of this leaf is used as passphrase for the key if
             it is encrypted.";
        }
      }
    }
  }
}
