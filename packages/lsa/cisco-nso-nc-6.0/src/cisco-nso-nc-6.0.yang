module cisco-nso-nc-6.0 {
  yang-version 1.1;
  namespace "http://tail-f.com/ns/ned-id/cisco-nso-nc-6.0";
  prefix cisco-nso-nc-6.0;

  import cisco-nso-nc {
    prefix family;
  }

  identity cisco-nso-nc-6.0 {
    base family:cisco-nso-nc;
  }
}
