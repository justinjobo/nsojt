module tailf-yang-patch-ncs {
  namespace "http://tail-f.com/ns/yang-patch/ncs";
  prefix ncsypatch;

  import tailf-yang-patch {
    prefix tfypatch;
  }
  import tailf-ncs {
    prefix ncs;
  }
  import tailf-common {
    prefix tailf;
  }

  organization "Tail-f Systems";

  description
    "This module defines extensions to RESTCONF for NCS.

     Copyright 2022-2023 Cisco Systems, Inc.
     All rights reserved.
     Permission is hereby granted to redistribute this file without
     modification.";

  revision 2023-01-17 {
    description
      "Released as part of NCS-6.0.2.

       Initial release.";
  }

  augment "/tfypatch:ypstatus/tfypatch:yang-patch-status"
          + "/tfypatch:global-status/tfypatch:ok" {
    // Used internally for YANG-Patch replies.
    uses ncs:ncs-commit-result;
  }
}
